FME workspace translate_all_recordtypes_to_mdb.fmw

Parameters:
- SourceDataset_CSV = C:\Users\zool1301\Documents\DHS\Phase6\ExtractedSurveyRecords_Python\*.All.csv   # Source CSV (CommaSeparatedValue) File(s)
- DestDataset_MDB_ADO = C:\Users\zool1301\Documents\DHS\Phase6\fmetest\db\test_joined_files.mdb   # Destination Microsoft Access Database File

Readers:
- CSV_1: CSV from $(SourceDataset_CSV)

Writers:
- MDB_ADO_1: MDB_ADO to $(DestDataset_MDB_ADO)

RECH6.All (reader CSV_1)
    attributes: FileCode char(7), HHID char(6), HC0 number(3,0), HC1 number(3,0), HC2 number(5,0), HC3 number(5,0), HC4 number(5,0), HC5 number(5,0), HC6 number(6,0), HC7 number(5,0), HC8 number(5,0), HC9 number(6,0), HC10 number(5,0), HC11 number(5,0), HC12 number(6,0), HC13 number(2,0), HC15 number(2,0), HC16 number(3,0), HC17 number(3,0), HC18 number(3,0), HC19 number(5,0), HC27 number(2,0), HC30 number(3,0), HC31 number(5,0), HC32 number(5,0), HC33 number(2,0), HC51 number(3,0), HC52 number(2,0), HC53 number(4,0), HC55 number(2,0),
      HC56 number(4,0), HC57 number(2,0), HC58 char(1), HC60 number(4,0), HC61 number(2,0), HC62 number(3,0), HC63 number(4,0), HC64 number(3,0), SHB13 char(1), HC68 number(2,0), HC70 number(5,0), HC71 number(5,0), HC72 number(5,0), HC73 number(5,0)
    -> RECH6_All (writer MDB_ADO_1)
RECH6_All (writer MDB_ADO_1)
    attributes: FileCode text(7), HHID text(6), HC0 decimal(3,0), HC1 decimal(3,0), HC2 decimal(5,0), HC3 decimal(5,0), HC4 decimal(5,0), HC5 decimal(5,0), HC6 decimal(6,0), HC7 decimal(5,0), HC8 decimal(5,0), HC9 decimal(6,0), HC10 decimal(5,0), HC11 decimal(5,0), HC12 decimal(6,0), HC13 decimal(2,0), HC15 decimal(2,0), HC16 decimal(3,0), HC17 decimal(3,0), HC18 decimal(3,0), HC19 decimal(5,0), HC27 decimal(2,0), HC30 decimal(3,0), HC31 decimal(5,0), HC32 decimal(5,0), HC33 decimal(2,0), HC51 decimal(3,0), HC52 decimal(2,0), HC53 decimal(4,0), HC55 decimal(2,0),
      HC56 decimal(4,0), HC57 decimal(2,0), HC58 text(1), HC60 decimal(4,0), HC61 decimal(2,0), HC62 decimal(3,0), HC63 decimal(4,0), HC64 decimal(3,0), SHB13 text(1), HC68 decimal(2,0), HC70 decimal(5,0), HC71 decimal(5,0), HC72 decimal(5,0), HC73 decimal(5,0)
REC92.All (reader CSV_1)
    attributes: FileCode char(7), CASEID char(12), IDX92 number(3,0), S222 number(2,0)
    -> REC92_All (writer MDB_ADO_1)
REC92_All (writer MDB_ADO_1)
    attributes: FileCode text(7), CASEID text(12), IDX92 decimal(3,0), S222 decimal(2,0)
REC11.All (reader CSV_1)
    attributes: FileCode char(7), CASEID char(9), V101 number(2,0), V102 number(2,0), V103 char(1), V104 char(1), V105 char(1), V106 number(2,0), V107 number(2,0), V113 number(3,0), V115 number(4,0), V116 number(3,0), V119 number(2,0), V120 number(2,0), V121 number(2,0), V122 number(2,0), V123 number(2,0), V124 number(2,0), V125 char(1), V127 number(3,0), V128 number(3,0), V129 number(3,0), V130 number(2,0), V131 char(1), V133 number(3,0), V134 number(2,0), V135 number(2,0), V136 number(3,0), V137 number(2,0), V138 number(2,0),
      V139 number(3,0), V140 number(2,0), V141 number(2,0), V149 number(2,0), V150 number(3,0), V151 number(2,0), V152 number(3,0), V153 number(2,0), AWFACTT number(5,0), AWFACTU number(5,0), AWFACTR number(5,0), AWFACTE number(5,0), AWFACTW number(5,0), V155 number(2,0), V156 char(1), V157 number(2,0), V158 number(2,0), V159 number(2,0), V160 number(2,0), V161 number(3,0), V166 char(1), V167 char(1), V168 char(1), V190 number(2,0), V191 number(8,0), ML101 char(1)
    -> REC11_All (writer MDB_ADO_1)
REC11_All (writer MDB_ADO_1)
    attributes: FileCode text(7), CASEID text(9), V101 decimal(2,0), V102 decimal(2,0), V103 text(1), V104 text(1), V105 text(1), V106 decimal(2,0), V107 decimal(2,0), V113 decimal(3,0), V115 decimal(4,0), V116 decimal(3,0), V119 decimal(2,0), V120 decimal(2,0), V121 decimal(2,0), V122 decimal(2,0), V123 decimal(2,0), V124 decimal(2,0), V125 text(1), V127 decimal(3,0), V128 decimal(3,0), V129 decimal(3,0), V130 decimal(2,0), V131 text(1), V133 decimal(3,0), V134 decimal(2,0), V135 decimal(2,0), V136 decimal(3,0), V137 decimal(2,0), V138 decimal(2,0),
      V139 decimal(3,0), V140 decimal(2,0), V141 decimal(2,0), V149 decimal(2,0), V150 decimal(3,0), V151 decimal(2,0), V152 decimal(3,0), V153 decimal(2,0), AWFACTT decimal(5,0), AWFACTU decimal(5,0), AWFACTR decimal(5,0), AWFACTE decimal(5,0), AWFACTW decimal(5,0), V155 decimal(2,0), V156 text(1), V157 decimal(2,0), V158 decimal(2,0), V159 decimal(2,0), V160 decimal(2,0), V161 decimal(3,0), V166 text(1), V167 text(1), V168 text(1), V190 decimal(2,0), V191 decimal(8,0), ML101 text(1)
RECHI.All (reader CSV_1)
    attributes: FileCode char(7), HHID char(7), SHCOLB number(2,0), SH61 number(3,0), SH62 number(2,0), SH63 number(3,0)
    -> RECHI_All (writer MDB_ADO_1)
RECHI_All (writer MDB_ADO_1)
    attributes: FileCode text(7), HHID text(7), SHCOLB decimal(2,0), SH61 decimal(3,0), SH62 decimal(2,0), SH63 decimal(3,0)
REC84.All (reader CSV_1)
    attributes: FileCode char(7), CASEID char(9), MMC1 number(3,0), MMC2 number(3,0), MMC3 char(1), REC84_GROUP char(1), MMC4 char(1), MMC5 number(3,0)
    -> REC84_All (writer MDB_ADO_1)
REC84_All (writer MDB_ADO_1)
    attributes: FileCode text(7), CASEID text(9), MMC1 decimal(3,0), MMC2 decimal(3,0), MMC3 text(1), REC84_GROUP text(1), MMC4 text(1), MMC5 decimal(3,0)
REC51.All (reader CSV_1)
    attributes: FileCode char(7), CASEID char(9), V501 number(2,0), V502 number(2,0), V503 number(2,0), V504 number(2,0), V505 char(1), V506 char(1), V507 number(3,0), V508 number(5,0), V509 number(5,0), V510 number(2,0), V511 number(3,0), V512 number(3,0), V513 number(2,0), V525 number(3,0), V527 number(4,0), V528 number(3,0), V529 number(4,0), V530 number(2,0), V531 number(3,0), V532 number(2,0), V535 number(2,0), V536 number(2,0), V537 number(3,0), V538 char(1), V539 char(1), V540 char(1), V541 char(1)
    -> REC51_All (writer MDB_ADO_1)
REC51_All (writer MDB_ADO_1)
    attributes: FileCode text(7), CASEID text(9), V501 decimal(2,0), V502 decimal(2,0), V503 decimal(2,0), V504 decimal(2,0), V505 text(1), V506 text(1), V507 decimal(3,0), V508 decimal(5,0), V509 decimal(5,0), V510 decimal(2,0), V511 decimal(3,0), V512 decimal(3,0), V513 decimal(2,0), V525 decimal(3,0), V527 decimal(4,0), V528 decimal(3,0), V529 decimal(4,0), V530 decimal(2,0), V531 decimal(3,0), V532 decimal(2,0), V535 decimal(2,0), V536 decimal(2,0), V537 decimal(3,0), V538 text(1), V539 text(1), V540 text(1), V541 text(1)
REC43.All (reader CSV_1)
    attributes: FileCode char(7), CASEID char(9), HIDX number(2,0), H1 number(2,0), H2 number(2,0), H2D number(3,0), H2M number(3,0), H2Y number(5,0), H3 number(2,0), H3D number(3,0), H3M number(3,0), H3Y number(5,0), H4 number(2,0), H4D number(3,0), H4M number(3,0), H4Y number(5,0), H5 number(2,0), H5D number(3,0), H5M number(3,0), H5Y number(5,0), H6 number(2,0), H6D number(3,0), H6M number(3,0), H6Y number(5,0), H7 number(2,0), H7D number(3,0), H7M number(3,0), H7Y number(5,0), H8 number(2,0), H8D number(3,0),
      H8M number(3,0), H8Y number(5,0), H9 number(2,0), H9D number(3,0), H9M number(3,0), H9Y number(5,0), H0 number(2,0), H0D number(3,0), H0M number(3,0), H0Y number(5,0), H10 number(2,0), H11 number(2,0), H11B number(2,0), H12A number(2,0), H12B number(2,0), H12C number(2,0), H12D number(2,0), H12E number(2,0), H12F number(2,0), H12G number(2,0), H12H number(2,0), H12I number(2,0), H12J number(2,0), H12K number(2,0), H12L number(2,0), H12M number(2,0), H12N number(2,0), H12O number(2,0), H12P number(2,0), H12Q char(1),
      H12R char(1), H12S number(2,0), H12T number(2,0), H12U number(2,0), H12V number(2,0), H12W char(1), H12X number(2,0), H12Y number(2,0), H12Z number(2,0), H13 number(2,0), H13B char(1), H14 number(2,0), H15 char(1), H15A char(1), H15B char(1), H15C char(1), H15D char(1), H15E char(1), H15F char(1), H15G char(1), H15H char(1), H15I char(1), H15J char(1), H15K char(1), H15L char(1), H15M char(1), H20 char(1), H21A char(1), H21 char(1), H22 number(2,0),
      H31 number(2,0), H31B number(2,0), H31C number(2,0), H31D number(2,0), H31E number(2,0), H32A number(2,0), H32B number(2,0), H32C number(2,0), H32D number(2,0), H32E number(2,0), H32F number(2,0), H32G number(2,0), H32H number(2,0), H32I number(2,0), H32J number(2,0), H32K number(2,0), H32L number(2,0), H32M number(2,0), H32N number(2,0), H32O number(2,0), H32P number(2,0), H32Q char(1), H32R char(1), H32S number(2,0), H32T number(2,0), H32U number(2,0), H32V number(2,0), H32W number(2,0), H32X number(2,0), H32Y number(2,0),
      H32Z number(2,0), H33 number(2,0), H33D number(3,0), H33M number(3,0), H33Y number(5,0), H34 number(2,0), H35 char(1), H36A number(2,0), H36B number(2,0), H36C number(2,0), H36D number(2,0), H36E char(1), H36F char(1), H37A number(2,0), H37B number(2,0), H37C char(1), H37D number(2,0), H37E number(2,0), H37F char(1), H37G char(1), H37H number(2,0), H37I number(2,0), H37J number(2,0), H37K number(2,0), H37L number(2,0), H37M number(2,0), H37N number(2,0), H37O number(2,0), H37P number(2,0), H37X number(2,0),
      H37Y number(2,0), H37Z number(2,0), H38 number(2,0), H39 number(2,0), H40 char(1), H40D char(1), H40M char(1), H40Y char(1), H41A char(1), H41B char(1), H42 number(2,0), H43 number(2,0), H44A char(1), H44B char(1), H44C char(1), H45 char(1), H46A number(3,0), H46B char(1), H47 char(1)
    -> REC43_All (writer MDB_ADO_1)
REC43_All (writer MDB_ADO_1)
    attributes: FileCode text(7), CASEID text(9), HIDX decimal(2,0), H1 decimal(2,0), H2 decimal(2,0), H2D decimal(3,0), H2M decimal(3,0), H2Y decimal(5,0), H3 decimal(2,0), H3D decimal(3,0), H3M decimal(3,0), H3Y decimal(5,0), H4 decimal(2,0), H4D decimal(3,0), H4M decimal(3,0), H4Y decimal(5,0), H5 decimal(2,0), H5D decimal(3,0), H5M decimal(3,0), H5Y decimal(5,0), H6 decimal(2,0), H6D decimal(3,0), H6M decimal(3,0), H6Y decimal(5,0), H7 decimal(2,0), H7D decimal(3,0), H7M decimal(3,0), H7Y decimal(5,0), H8 decimal(2,0), H8D decimal(3,0),
      H8M decimal(3,0), H8Y decimal(5,0), H9 decimal(2,0), H9D decimal(3,0), H9M decimal(3,0), H9Y decimal(5,0), H0 decimal(2,0), H0D decimal(3,0), H0M decimal(3,0), H0Y decimal(5,0), H10 decimal(2,0), H11 decimal(2,0), H11B decimal(2,0), H12A decimal(2,0), H12B decimal(2,0), H12C decimal(2,0), H12D decimal(2,0), H12E decimal(2,0), H12F decimal(2,0), H12G decimal(2,0), H12H decimal(2,0), H12I decimal(2,0), H12J decimal(2,0), H12K decimal(2,0), H12L decimal(2,0), H12M decimal(2,0), H12N decimal(2,0), H12O decimal(2,0), H12P decimal(2,0), H12Q text(1),
      H12R text(1), H12S decimal(2,0), H12T decimal(2,0), H12U decimal(2,0), H12V decimal(2,0), H12W text(1), H12X decimal(2,0), H12Y decimal(2,0), H12Z decimal(2,0), H13 decimal(2,0), H13B text(1), H14 decimal(2,0), H15 text(1), H15A text(1), H15B text(1), H15C text(1), H15D text(1), H15E text(1), H15F text(1), H15G text(1), H15H text(1), H15I text(1), H15J text(1), H15K text(1), H15L text(1), H15M text(1), H20 text(1), H21A text(1), H21 text(1), H22 decimal(2,0),
      H31 decimal(2,0), H31B decimal(2,0), H31C decimal(2,0), H31D decimal(2,0), H31E decimal(2,0), H32A decimal(2,0), H32B decimal(2,0), H32C decimal(2,0), H32D decimal(2,0), H32E decimal(2,0), H32F decimal(2,0), H32G decimal(2,0), H32H decimal(2,0), H32I decimal(2,0), H32J decimal(2,0), H32K decimal(2,0), H32L decimal(2,0), H32M decimal(2,0), H32N decimal(2,0), H32O decimal(2,0), H32P decimal(2,0), H32Q text(1), H32R text(1), H32S decimal(2,0), H32T decimal(2,0), H32U decimal(2,0), H32V decimal(2,0), H32W decimal(2,0), H32X decimal(2,0), H32Y decimal(2,0),
      H32Z decimal(2,0), H33 decimal(2,0), H33D decimal(3,0), H33M decimal(3,0), H33Y decimal(5,0), H34 decimal(2,0), H35 text(1), H36A decimal(2,0), H36B decimal(2,0), H36C decimal(2,0), H36D decimal(2,0), H36E text(1), H36F text(1), H37A decimal(2,0), H37B decimal(2,0), H37C text(1), H37D decimal(2,0), H37E decimal(2,0), H37F text(1), H37G text(1), H37H decimal(2,0), H37I decimal(2,0), H37J decimal(2,0), H37K decimal(2,0), H37L decimal(2,0), H37M decimal(2,0), H37N decimal(2,0), H37O decimal(2,0), H37P decimal(2,0), H37X decimal(2,0),
      H37Y decimal(2,0), H37Z decimal(2,0), H38 decimal(2,0), H39 decimal(2,0), H40 text(1), H40D text(1), H40M text(1), H40Y text(1), H41A text(1), H41B text(1), H42 decimal(2,0), H43 decimal(2,0), H44A text(1), H44B text(1), H44C text(1), H45 text(1), H46A decimal(3,0), H46B text(1), H47 text(1)
RECH5.All (reader CSV_1)
    attributes: FileCode char(7), HHID char(6), HA0 number(3,0), HA1 number(3,0), HA2 number(5,0), HA3 number(5,0), HA4 number(5,0), HA5 number(5,0), HA6 number(6,0), HA11 number(5,0), HA12 number(6,0), HA12A number(6,0), HA12B number(6,0), HA13 number(2,0), HA32 number(5,0), HA33 number(2,0), HA35 char(1), HA40 number(5,0), HA41 number(5,0), HA50 char(1), HA51 char(1), HA52 number(2,0), HA53 number(4,0), HA54 number(2,0), HA55 number(2,0), HA56 number(4,0), HA57 number(2,0), HA58 char(1), HA60 char(1), HA61 char(1),
      HA62 char(1), HA63 char(1), HA64 char(1), HA65 number(2,0), HA66 number(2,0), HA67 number(3,0), HA68 number(2,0), HA69 char(1), HA70 char(1)
    -> RECH5_All (writer MDB_ADO_1)
RECH5_All (writer MDB_ADO_1)
    attributes: FileCode text(7), HHID text(6), HA0 decimal(3,0), HA1 decimal(3,0), HA2 decimal(5,0), HA3 decimal(5,0), HA4 decimal(5,0), HA5 decimal(5,0), HA6 decimal(6,0), HA11 decimal(5,0), HA12 decimal(6,0), HA12A decimal(6,0), HA12B decimal(6,0), HA13 decimal(2,0), HA32 decimal(5,0), HA33 decimal(2,0), HA35 text(1), HA40 decimal(5,0), HA41 decimal(5,0), HA50 text(1), HA51 text(1), HA52 decimal(2,0), HA53 decimal(4,0), HA54 decimal(2,0), HA55 decimal(2,0), HA56 decimal(4,0), HA57 decimal(2,0), HA58 text(1), HA60 text(1), HA61 text(1),
      HA62 text(1), HA63 text(1), HA64 text(1), HA65 decimal(2,0), HA66 decimal(2,0), HA67 decimal(3,0), HA68 decimal(2,0), HA69 text(1), HA70 text(1)
REC91.All (reader CSV_1)
    attributes: FileCode char(7), CASEID char(9), S28DAYS number(2,0), S5YEARS number(2,0), S103A number(2,0), S104A number(2,0), S112A number(2,0), S112B number(2,0), S114A number(2,0), S114B number(2,0), S114C number(2,0), S114D number(2,0), S114E number(2,0), S114F number(2,0), S114G number(2,0), S114GX number(3,0), S223A number(2,0), S223B number(2,0), S229A number(2,0), S229B number(2,0), S229C number(2,0), S229D number(3,0), S306A number(2,0), S325J number(2,0), S325M number(2,0), S325N number(2,0), S325O number(2,0), S325A number(2,0), S325B number(2,0), S325CA number(2,0),
      S325CB number(2,0), S325CC number(2,0), S325CD number(2,0), S325CE number(2,0), S325CF number(2,0), S325CG number(2,0), S325CH number(2,0), S325CX number(2,0), S325CZ number(2,0), S325D number(2,0), S325E number(2,0), S325FA number(2,0), S325FB number(2,0), S325FC number(2,0), S325FD number(2,0), S325FE number(2,0), S325FF number(2,0), S325FH number(2,0), S325FX number(2,0), S325FZ number(2,0), S326 number(2,0), S326AA number(2,0), S326AB number(2,0), S326AC number(2,0), S326AX number(2,0), S326B number(3,0), S326C number(2,0), S506A char(1), S604A number(3,0), S616 number(3,0),
      S714AA number(2,0), S714BA number(2,0), S714BB number(2,0), S714BC number(2,0), S714D number(2,0), S714E number(2,0), S803A number(2,0), S823 number(2,0), S823A number(2,0), S823B number(2,0), S906A number(2,0), S906B number(2,0), S937A number(2,0), S937B number(2,0), S945O number(2,0), S945A number(2,0), S1001 number(2,0), S1002 number(2,0), S1003 number(2,0), S1004 number(2,0), S1005 number(2,0), SCORE number(3,0), AWFACTE2 number(5,0), AWFACTE3 number(5,0)
    -> REC91_All (writer MDB_ADO_1)
REC91_All (writer MDB_ADO_1)
    attributes: FileCode text(7), CASEID text(9), S28DAYS decimal(2,0), S5YEARS decimal(2,0), S103A decimal(2,0), S104A decimal(2,0), S112A decimal(2,0), S112B decimal(2,0), S114A decimal(2,0), S114B decimal(2,0), S114C decimal(2,0), S114D decimal(2,0), S114E decimal(2,0), S114F decimal(2,0), S114G decimal(2,0), S114GX decimal(3,0), S223A decimal(2,0), S223B decimal(2,0), S229A decimal(2,0), S229B decimal(2,0), S229C decimal(2,0), S229D decimal(3,0), S306A decimal(2,0), S325J decimal(2,0), S325M decimal(2,0), S325N decimal(2,0), S325O decimal(2,0), S325A decimal(2,0), S325B decimal(2,0), S325CA decimal(2,0),
      S325CB decimal(2,0), S325CC decimal(2,0), S325CD decimal(2,0), S325CE decimal(2,0), S325CF decimal(2,0), S325CG decimal(2,0), S325CH decimal(2,0), S325CX decimal(2,0), S325CZ decimal(2,0), S325D decimal(2,0), S325E decimal(2,0), S325FA decimal(2,0), S325FB decimal(2,0), S325FC decimal(2,0), S325FD decimal(2,0), S325FE decimal(2,0), S325FF decimal(2,0), S325FH decimal(2,0), S325FX decimal(2,0), S325FZ decimal(2,0), S326 decimal(2,0), S326AA decimal(2,0), S326AB decimal(2,0), S326AC decimal(2,0), S326AX decimal(2,0), S326B decimal(3,0), S326C decimal(2,0), S506A text(1), S604A decimal(3,0), S616 decimal(3,0),
      S714AA decimal(2,0), S714BA decimal(2,0), S714BB decimal(2,0), S714BC decimal(2,0), S714D decimal(2,0), S714E decimal(2,0), S803A decimal(2,0), S823 decimal(2,0), S823A decimal(2,0), S823B decimal(2,0), S906A decimal(2,0), S906B decimal(2,0), S937A decimal(2,0), S937B decimal(2,0), S945O decimal(2,0), S945A decimal(2,0), S1001 decimal(2,0), S1002 decimal(2,0), S1003 decimal(2,0), S1004 decimal(2,0), S1005 decimal(2,0), SCORE decimal(3,0), AWFACTE2 decimal(5,0), AWFACTE3 decimal(5,0)
RECHDP2.All (reader CSV_1)
    attributes: FileCode char(7), HHID char(6), HDPIDX2 number(2,0), SH197B number(3,0), SH197C number(2,0), SH197D number(2,0), SH197E number(2,0)
    -> RECHDP2_All (writer MDB_ADO_1)
RECHDP2_All (writer MDB_ADO_1)
    attributes: FileCode text(7), HHID text(6), HDPIDX2 decimal(2,0), SH197B decimal(3,0), SH197C decimal(2,0), SH197D decimal(2,0), SH197E decimal(2,0)
REC83.All (reader CSV_1)
    attributes: FileCode char(7), CASEID char(9), MMIDX number(3,0), MM1 number(2,0), MM2 number(2,0), MM3 number(3,0), MM4 number(5,0), MM5 char(1), MM6 number(3,0), MM7 number(3,0), MM8 number(5,0), MM9 number(3,0), MM10 char(1), MM11 char(1), MM12 char(1), MM13 char(1), MM14 number(3,0), MM15 char(1)
    -> REC83_All (writer MDB_ADO_1)
REC83_All (writer MDB_ADO_1)
    attributes: FileCode text(7), CASEID text(9), MMIDX decimal(3,0), MM1 decimal(2,0), MM2 decimal(2,0), MM3 decimal(3,0), MM4 decimal(5,0), MM5 text(1), MM6 decimal(3,0), MM7 decimal(3,0), MM8 decimal(5,0), MM9 decimal(3,0), MM10 text(1), MM11 text(1), MM12 text(1), MM13 text(1), MM14 decimal(3,0), MM15 text(1)
RECHMC.All (reader CSV_1)
    attributes: FileCode char(7), HHID number(6,0), IDXHML number(2,0), SH123A number(2,0), SH123B number(3,0), SH123C number(2,0), SH123D number(2,0), SH125A number(2,0), SH127A number(2,0), SH127B number(5,0), SH128 number(3,0), SH128A number(2,0), SH128B number(5,0)
    -> RECHMC_All (writer MDB_ADO_1)
RECHMC_All (writer MDB_ADO_1)
    attributes: FileCode text(7), HHID decimal(6,0), IDXHML decimal(2,0), SH123A decimal(2,0), SH123B decimal(3,0), SH123C decimal(2,0), SH123D decimal(2,0), SH125A decimal(2,0), SH127A decimal(2,0), SH127B decimal(5,0), SH128 decimal(3,0), SH128A decimal(2,0), SH128B decimal(5,0)
REC75.All (reader CSV_1)
    attributes: FileCode char(7), CASEID char(9), V750 number(2,0), V751 number(2,0), V754BP char(1), V754CP number(2,0), V754DP number(2,0), V754JP number(2,0), V754WP number(2,0), V756 number(2,0), V761 char(1), V761B char(1), V761C char(1), V762AA char(1), V762AB char(1), V762AC char(1), V762AD char(1), V762AE char(1), V762AF char(1), V762AG char(1), V762AH char(1), V762AI char(1), V762AJ char(1), V762AK char(1), V762AL char(1), V762AM char(1), V762AN char(1), V762AO char(1), V762AP char(1), V762AQ char(1),
      V762AR char(1), V762AS char(1), V762AT char(1), V762AU char(1), V762AV char(1), V762AW char(1), V762AX char(1), V762AZ char(1), V762BA char(1), V762BB char(1), V762BC char(1), V762BD char(1), V762BE char(1), V762BF char(1), V762BG char(1), V762BH char(1), V762BI char(1), V762BJ char(1), V762BK char(1), V762BL char(1), V762BM char(1), V762BN char(1), V762BO char(1), V762BP char(1), V762BQ char(1), V762BR char(1), V762BS char(1), V762BT char(1), V762BU char(1), V762BV char(1),
      V762BW char(1), V762BX char(1), V762BZ char(1), V763A number(2,0), V763B number(2,0), V763C number(2,0), V763D char(1), V763E char(1), V763F char(1), V763G char(1), V766A char(1), V766B char(1), V767A char(1), V767B char(1), V767C char(1), V768A char(1), V768B char(1), V768C char(1), V769 char(1), V769A char(1), V770 number(2,0), V770A number(2,0), V770B number(2,0), V770C number(2,0), V770D number(2,0), V770E number(2,0), V770F number(2,0), V770G number(2,0), V770H number(2,0), V770I number(2,0),
      V770J number(2,0), V770K char(1), V770L number(2,0), V770M number(2,0), V770N number(2,0), V770O number(2,0), V770P number(2,0), V770Q number(2,0), V770R number(2,0), V770S number(2,0), V770T number(2,0), V770U number(2,0), V770V number(2,0), V770W number(2,0), V770X number(2,0), V774A number(2,0), V774B number(2,0), V774C number(2,0), V775 char(1), V777 char(1), V778 char(1), V779 char(1), V780 char(1), V781 char(1), V783 char(1), V784A char(1), V784B char(1), V784C char(1), V784D char(1), V784E char(1),
      V784F char(1), V784G char(1), V784H char(1), V784I char(1), V784J char(1), V784K char(1), V784L char(1), V784M char(1), V784N char(1), V784O char(1), V784P char(1), V784Q char(1), V784R char(1), V784S char(1), V784T char(1), V784U char(1), V784V char(1), V784X char(1), V785 number(2,0)
    -> REC75_All (writer MDB_ADO_1)
REC75_All (writer MDB_ADO_1)
    attributes: FileCode text(7), CASEID text(9), V750 decimal(2,0), V751 decimal(2,0), V754BP text(1), V754CP decimal(2,0), V754DP decimal(2,0), V754JP decimal(2,0), V754WP decimal(2,0), V756 decimal(2,0), V761 text(1), V761B text(1), V761C text(1), V762AA text(1), V762AB text(1), V762AC text(1), V762AD text(1), V762AE text(1), V762AF text(1), V762AG text(1), V762AH text(1), V762AI text(1), V762AJ text(1), V762AK text(1), V762AL text(1), V762AM text(1), V762AN text(1), V762AO text(1), V762AP text(1), V762AQ text(1),
      V762AR text(1), V762AS text(1), V762AT text(1), V762AU text(1), V762AV text(1), V762AW text(1), V762AX text(1), V762AZ text(1), V762BA text(1), V762BB text(1), V762BC text(1), V762BD text(1), V762BE text(1), V762BF text(1), V762BG text(1), V762BH text(1), V762BI text(1), V762BJ text(1), V762BK text(1), V762BL text(1), V762BM text(1), V762BN text(1), V762BO text(1), V762BP text(1), V762BQ text(1), V762BR text(1), V762BS text(1), V762BT text(1), V762BU text(1), V762BV text(1),
      V762BW text(1), V762BX text(1), V762BZ text(1), V763A decimal(2,0), V763B decimal(2,0), V763C decimal(2,0), V763D text(1), V763E text(1), V763F text(1), V763G text(1), V766A text(1), V766B text(1), V767A text(1), V767B text(1), V767C text(1), V768A text(1), V768B text(1), V768C text(1), V769 text(1), V769A text(1), V770 decimal(2,0), V770A decimal(2,0), V770B decimal(2,0), V770C decimal(2,0), V770D decimal(2,0), V770E decimal(2,0), V770F decimal(2,0), V770G decimal(2,0), V770H decimal(2,0), V770I decimal(2,0),
      V770J decimal(2,0), V770K text(1), V770L decimal(2,0), V770M decimal(2,0), V770N decimal(2,0), V770O decimal(2,0), V770P decimal(2,0), V770Q decimal(2,0), V770R decimal(2,0), V770S decimal(2,0), V770T decimal(2,0), V770U decimal(2,0), V770V decimal(2,0), V770W decimal(2,0), V770X decimal(2,0), V774A decimal(2,0), V774B decimal(2,0), V774C decimal(2,0), V775 text(1), V777 text(1), V778 text(1), V779 text(1), V780 text(1), V781 text(1), V783 text(1), V784A text(1), V784B text(1), V784C text(1), V784D text(1), V784E text(1),
      V784F text(1), V784G text(1), V784H text(1), V784I text(1), V784J text(1), V784K text(1), V784L text(1), V784M text(1), V784N text(1), V784O text(1), V784P text(1), V784Q text(1), V784R text(1), V784S text(1), V784T text(1), V784U text(1), V784V text(1), V784X text(1), V785 decimal(2,0)
REC42.All (reader CSV_1)
    attributes: FileCode char(7), CASEID char(9), V401 number(2,0), V404 number(2,0), V405 number(2,0), V406 number(2,0), V407 char(1), V408 char(1), V409 number(2,0), V409A char(1), V410 number(2,0), V410A char(1), V411 number(2,0), V411A number(2,0), V412 char(1), V412A number(2,0), V412B char(1), V412C char(1), V413 number(2,0), V413A char(1), V413B char(1), V413C char(1), V413D char(1), V414A char(1), V414B char(1), V414C char(1), V414D char(1), V414E number(2,0), V414F number(2,0), V414G number(2,0),
      V414H number(2,0), V414I number(2,0), V414J number(2,0), V414K number(2,0), V414L number(2,0), V414M number(2,0), V414N number(2,0), V414O number(2,0), V414P number(2,0), V414Q char(1), V414R char(1), V414S number(2,0), V414T char(1), V414U char(1), V414V number(2,0), V414W char(1), V415 number(2,0), V416 char(1), V417 number(2,0), V418 number(2,0), V419 number(2,0), V420 char(1), V421 char(1), V426 number(4,0), V437 number(5,0), V438 number(5,0), V439 number(5,0), V440 number(5,0), V441 number(6,0), V442 number(6,0),
      V443 number(6,0), V444 number(6,0), V444A number(5,0), V445 number(5,0), V446 number(5,0), V447 number(2,0), V447A number(3,0), V452A char(1), V452B char(1), V452C number(2,0), V453 number(4,0), V454 number(2,0), V455 number(2,0), V456 number(4,0), V457 number(2,0), V458 char(1), V459 char(1), V460 char(1), V461 char(1), V462 char(1), V463A char(1), V463B char(1), V463C char(1), V463D char(1), V463E char(1), V463F char(1), V463G char(1), V463X char(1), V463Z char(1), V464 char(1),
      V465 char(1), V466 char(1), V467A char(1), V467B char(1), V467C char(1), V467D char(1), V467E char(1), V467F char(1), V467G char(1), V467H char(1), V467I char(1), V467J char(1), V467K char(1), V467L char(1), V467M char(1), V468 number(2,0), V469E number(2,0), V469F number(2,0), V469X number(2,0), V471A char(1), V471B char(1), V471C char(1), V471D char(1), V471E char(1), V471F char(1), V471G char(1), V472A char(1), V472B char(1), V472C char(1), V472D char(1),
      V472E char(1), V472F char(1), V472G char(1), V472H char(1), V472I char(1), V472J char(1), V472K char(1), V472L char(1), V472M char(1), V472N char(1), V472O char(1), V472P char(1), V472Q char(1), V472R char(1), V472S char(1), V472T char(1), V472U char(1), V473A char(1), V473B char(1), V474 char(1), V474A char(1), V474B char(1), V474C char(1), V474D char(1), V474E char(1), V474F char(1), V474G char(1), V474H char(1), V474I char(1), V474J char(1),
      V474X char(1), V474Z char(1), V475 char(1), V476 char(1), V477 char(1), V478 char(1), V479 char(1), V480 char(1), V481 char(1), V481A char(1), V481B char(1), V481C char(1), V481D char(1), V481E char(1), V481F char(1), V481G char(1), V481H char(1), V481X char(1), V482A char(1), V482B char(1), V482C char(1)
    -> REC42_All (writer MDB_ADO_1)
REC42_All (writer MDB_ADO_1)
    attributes: FileCode text(7), CASEID text(9), V401 decimal(2,0), V404 decimal(2,0), V405 decimal(2,0), V406 decimal(2,0), V407 text(1), V408 text(1), V409 decimal(2,0), V409A text(1), V410 decimal(2,0), V410A text(1), V411 decimal(2,0), V411A decimal(2,0), V412 text(1), V412A decimal(2,0), V412B text(1), V412C text(1), V413 decimal(2,0), V413A text(1), V413B text(1), V413C text(1), V413D text(1), V414A text(1), V414B text(1), V414C text(1), V414D text(1), V414E decimal(2,0), V414F decimal(2,0), V414G decimal(2,0),
      V414H decimal(2,0), V414I decimal(2,0), V414J decimal(2,0), V414K decimal(2,0), V414L decimal(2,0), V414M decimal(2,0), V414N decimal(2,0), V414O decimal(2,0), V414P decimal(2,0), V414Q text(1), V414R text(1), V414S decimal(2,0), V414T text(1), V414U text(1), V414V decimal(2,0), V414W text(1), V415 decimal(2,0), V416 text(1), V417 decimal(2,0), V418 decimal(2,0), V419 decimal(2,0), V420 text(1), V421 text(1), V426 decimal(4,0), V437 decimal(5,0), V438 decimal(5,0), V439 decimal(5,0), V440 decimal(5,0), V441 decimal(6,0), V442 decimal(6,0),
      V443 decimal(6,0), V444 decimal(6,0), V444A decimal(5,0), V445 decimal(5,0), V446 decimal(5,0), V447 decimal(2,0), V447A decimal(3,0), V452A text(1), V452B text(1), V452C decimal(2,0), V453 decimal(4,0), V454 decimal(2,0), V455 decimal(2,0), V456 decimal(4,0), V457 decimal(2,0), V458 text(1), V459 text(1), V460 text(1), V461 text(1), V462 text(1), V463A text(1), V463B text(1), V463C text(1), V463D text(1), V463E text(1), V463F text(1), V463G text(1), V463X text(1), V463Z text(1), V464 text(1),
      V465 text(1), V466 text(1), V467A text(1), V467B text(1), V467C text(1), V467D text(1), V467E text(1), V467F text(1), V467G text(1), V467H text(1), V467I text(1), V467J text(1), V467K text(1), V467L text(1), V467M text(1), V468 decimal(2,0), V469E decimal(2,0), V469F decimal(2,0), V469X decimal(2,0), V471A text(1), V471B text(1), V471C text(1), V471D text(1), V471E text(1), V471F text(1), V471G text(1), V472A text(1), V472B text(1), V472C text(1), V472D text(1),
      V472E text(1), V472F text(1), V472G text(1), V472H text(1), V472I text(1), V472J text(1), V472K text(1), V472L text(1), V472M text(1), V472N text(1), V472O text(1), V472P text(1), V472Q text(1), V472R text(1), V472S text(1), V472T text(1), V472U text(1), V473A text(1), V473B text(1), V474 text(1), V474A text(1), V474B text(1), V474C text(1), V474D text(1), V474E text(1), V474F text(1), V474G text(1), V474H text(1), V474I text(1), V474J text(1),
      V474X text(1), V474Z text(1), V475 text(1), V476 text(1), V477 text(1), V478 text(1), V479 text(1), V480 text(1), V481 text(1), V481A text(1), V481B text(1), V481C text(1), V481D text(1), V481E text(1), V481F text(1), V481G text(1), V481H text(1), V481X text(1), V482A text(1), V482B text(1), V482C text(1)
RECHCHL.All (reader CSV_1)
    attributes: FileCode char(7), HHID char(9), IDXCHL number(3,0), CHL1 number(2,0), CHL2 number(3,0), CHL3 number(2,0), CHL4 number(3,0), CHL5 number(2,0), CHL6 number(3,0), CHL7 number(2,0), CHL8 number(3,0)
    -> RECHCHL_All (writer MDB_ADO_1)
RECHCHL_All (writer MDB_ADO_1)
    attributes: FileCode text(7), HHID text(9), IDXCHL decimal(3,0), CHL1 decimal(2,0), CHL2 decimal(3,0), CHL3 decimal(2,0), CHL4 decimal(3,0), CHL5 decimal(2,0), CHL6 decimal(3,0), CHL7 decimal(2,0), CHL8 decimal(3,0)
RECHML.All (reader CSV_1)
    attributes: FileCode char(7), HHID char(6), HMLIDX number(2,0), HML3 number(2,0), HML4 number(3,0), HML5 number(2,0), HML6 number(2,0), HML7 number(3,0), HML8 number(2,0), HML9 number(3,0), HML10 number(2,0), HML11 number(2,0), HML21 number(2,0), HMLA number(3,0), HMLB number(3,0), HMLC number(3,0), HMLD number(3,0), HMLE char(1)
    -> RECHML_All (writer MDB_ADO_1)
RECHML_All (writer MDB_ADO_1)
    attributes: FileCode text(7), HHID text(6), HMLIDX decimal(2,0), HML3 decimal(2,0), HML4 decimal(3,0), HML5 decimal(2,0), HML6 decimal(2,0), HML7 decimal(3,0), HML8 decimal(2,0), HML9 decimal(3,0), HML10 decimal(2,0), HML11 decimal(2,0), HML21 decimal(2,0), HMLA decimal(3,0), HMLB decimal(3,0), HMLC decimal(3,0), HMLD decimal(3,0), HMLE text(1)
RECH4.All (reader CSV_1)
    attributes: FileCode char(7), HHID char(5), IDXH4 number(3,0), SH08 number(2,0), SH13 number(2,0), SH18 number(2,0), SH19 number(2,0), SH20 number(2,0), SH21 number(2,0), SH22 number(2,0)
    -> RECH4_All (writer MDB_ADO_1)
RECH4_All (writer MDB_ADO_1)
    attributes: FileCode text(7), HHID text(5), IDXH4 decimal(3,0), SH08 decimal(2,0), SH13 decimal(2,0), SH18 decimal(2,0), SH19 decimal(2,0), SH20 decimal(2,0), SH21 decimal(2,0), SH22 decimal(2,0)
REC82.All (reader CSV_1)
    attributes: FileCode char(7), CASEID char(9), VCOL number(2,0), VCAL char(73)
    -> REC82_All (writer MDB_ADO_1)
REC82_All (writer MDB_ADO_1)
    attributes: FileCode text(7), CASEID text(9), VCOL decimal(2,0), VCAL text(73)
REC01.All (reader CSV_1)
    attributes: FileCode char(7), CASEID char(9), V000 char(4), V001 number(3,0), V002 number(4,0), V003 number(3,0), V004 number(3,0), V005 number(7,0), V006 number(3,0), V007 number(5,0), V008 number(5,0), V009 number(3,0), V010 number(5,0), V011 number(5,0), V012 number(3,0), V013 number(2,0), V014 number(2,0), V015 number(2,0), V016 number(3,0), V017 number(5,0), V018 number(3,0), V019 number(3,0), V019A number(2,0), V020 number(2,0), V021 number(3,0), V022 number(3,0), V023 number(3,0), V024 number(2,0), V025 number(2,0), V026 number(2,0),
      V027 number(2,0), V028 number(4,0), V029 number(2,0), V030 number(3,0), V031 number(3,0), V032 number(2,0), V034 number(3,0), V040 number(3,0), V042 number(2,0), V044 char(1)
    -> REC01_All (writer MDB_ADO_1)
REC01_All (writer MDB_ADO_1)
    attributes: FileCode text(7), CASEID text(9), V000 text(4), V001 decimal(3,0), V002 decimal(4,0), V003 decimal(3,0), V004 decimal(3,0), V005 decimal(7,0), V006 decimal(3,0), V007 decimal(5,0), V008 decimal(5,0), V009 decimal(3,0), V010 decimal(5,0), V011 decimal(5,0), V012 decimal(3,0), V013 decimal(2,0), V014 decimal(2,0), V015 decimal(2,0), V016 decimal(3,0), V017 decimal(5,0), V018 decimal(3,0), V019 decimal(3,0), V019A decimal(2,0), V020 decimal(2,0), V021 decimal(3,0), V022 decimal(3,0), V023 decimal(3,0), V024 decimal(2,0), V025 decimal(2,0), V026 decimal(2,0),
      V027 decimal(2,0), V028 decimal(4,0), V029 decimal(2,0), V030 decimal(3,0), V031 decimal(3,0), V032 decimal(2,0), V034 decimal(3,0), V040 decimal(3,0), V042 decimal(2,0), V044 text(1)
REC41.All (reader CSV_1)
    attributes: FileCode char(7), CASEID char(9), MIDX number(2,0), M1 number(2,0), M1A number(2,0), M1B char(1), M1C char(1), M1D number(3,0), M1E number(5,0), M2A number(2,0), M2B number(2,0), M2C number(2,0), M2D number(2,0), M2E number(2,0), M2F number(2,0), M2G number(2,0), M2H number(2,0), M2I number(2,0), M2J char(1), M2K number(2,0), M2L number(2,0), M2M number(2,0), M2N number(2,0), M3A number(2,0), M3B number(2,0), M3C number(2,0), M3D number(2,0), M3E number(2,0), M3F number(2,0), M3G number(2,0),
      M3H number(2,0), M3I number(2,0), M3J number(2,0), M3K number(2,0), M3L number(2,0), M3M number(2,0), M3N number(2,0), M4 number(3,0), M5 number(3,0), M6 number(3,0), M7 number(3,0), M8 number(3,0), M9 number(3,0), M10 number(2,0), M11 number(4,0), M13 char(1), M14 number(3,0), M15 number(3,0), M17 number(2,0), M18 number(2,0), M19 char(1), M19A char(1), M27 number(2,0), M28 number(2,0), M29 number(2,0), M34 number(4,0), M35 char(1), M36 char(1), M38 number(2,0), M39A number(2,0),
      M39 number(2,0), M42A char(1), M42B char(1), M42C char(1), M42D char(1), M42E char(1), M43 number(2,0), M44 char(1), M45 char(1), M46 char(1), M47 char(1), M48 char(1), M49A char(1), M49B char(1), M49C char(1), M49D char(1), M49E char(1), M49F char(1), M49G char(1), M49X char(1), M49Z char(1), M49Y char(1), M50 number(2,0), M51 number(4,0), M52 number(3,0), M54 number(2,0), M55A number(2,0), M55B number(2,0), M55C number(2,0), M55D number(2,0),
      M55E number(2,0), M55F number(2,0), M55G number(2,0), M55H number(2,0), M55I number(2,0), M55J number(2,0), M55K number(2,0), M55L char(1), M55M char(1), M55N char(1), M55O char(1), M55X number(2,0), M55Z number(2,0), M57A number(2,0), M57B char(1), M57C char(1), M57D char(1), M57E number(2,0), M57F number(2,0), M57G number(2,0), M57H number(2,0), M57I number(2,0), M57J number(2,0), M57K number(2,0), M57L number(2,0), M57M number(2,0), M57N number(2,0), M57O number(2,0), M57P number(2,0), M57Q number(2,0),
      M57R number(2,0), M57S number(2,0), M57T number(2,0), M57U char(1), M57V char(1), M57X number(2,0), M60 char(1), M61 number(4,0), M62 number(2,0), M65A char(1), M65B char(1), M65C char(1), M65D char(1), M65E char(1), M65F char(1), M65G char(1), M65H char(1), M65I char(1), M65J char(1), M65K char(1), M65L char(1), M65X char(1), M66 number(2,0), M70 number(2,0), M71 number(4,0), M72 number(3,0), M73 number(3,0)
    -> REC41_All (writer MDB_ADO_1)
REC41_All (writer MDB_ADO_1)
    attributes: FileCode text(7), CASEID text(9), MIDX decimal(2,0), M1 decimal(2,0), M1A decimal(2,0), M1B text(1), M1C text(1), M1D decimal(3,0), M1E decimal(5,0), M2A decimal(2,0), M2B decimal(2,0), M2C decimal(2,0), M2D decimal(2,0), M2E decimal(2,0), M2F decimal(2,0), M2G decimal(2,0), M2H decimal(2,0), M2I decimal(2,0), M2J text(1), M2K decimal(2,0), M2L decimal(2,0), M2M decimal(2,0), M2N decimal(2,0), M3A decimal(2,0), M3B decimal(2,0), M3C decimal(2,0), M3D decimal(2,0), M3E decimal(2,0), M3F decimal(2,0), M3G decimal(2,0),
      M3H decimal(2,0), M3I decimal(2,0), M3J decimal(2,0), M3K decimal(2,0), M3L decimal(2,0), M3M decimal(2,0), M3N decimal(2,0), M4 decimal(3,0), M5 decimal(3,0), M6 decimal(3,0), M7 decimal(3,0), M8 decimal(3,0), M9 decimal(3,0), M10 decimal(2,0), M11 decimal(4,0), M13 text(1), M14 decimal(3,0), M15 decimal(3,0), M17 decimal(2,0), M18 decimal(2,0), M19 text(1), M19A text(1), M27 decimal(2,0), M28 decimal(2,0), M29 decimal(2,0), M34 decimal(4,0), M35 text(1), M36 text(1), M38 decimal(2,0), M39A decimal(2,0),
      M39 decimal(2,0), M42A text(1), M42B text(1), M42C text(1), M42D text(1), M42E text(1), M43 decimal(2,0), M44 text(1), M45 text(1), M46 text(1), M47 text(1), M48 text(1), M49A text(1), M49B text(1), M49C text(1), M49D text(1), M49E text(1), M49F text(1), M49G text(1), M49X text(1), M49Z text(1), M49Y text(1), M50 decimal(2,0), M51 decimal(4,0), M52 decimal(3,0), M54 decimal(2,0), M55A decimal(2,0), M55B decimal(2,0), M55C decimal(2,0), M55D decimal(2,0),
      M55E decimal(2,0), M55F decimal(2,0), M55G decimal(2,0), M55H decimal(2,0), M55I decimal(2,0), M55J decimal(2,0), M55K decimal(2,0), M55L text(1), M55M text(1), M55N text(1), M55O text(1), M55X decimal(2,0), M55Z decimal(2,0), M57A decimal(2,0), M57B text(1), M57C text(1), M57D text(1), M57E decimal(2,0), M57F decimal(2,0), M57G decimal(2,0), M57H decimal(2,0), M57I decimal(2,0), M57J decimal(2,0), M57K decimal(2,0), M57L decimal(2,0), M57M decimal(2,0), M57N decimal(2,0), M57O decimal(2,0), M57P decimal(2,0), M57Q decimal(2,0),
      M57R decimal(2,0), M57S decimal(2,0), M57T decimal(2,0), M57U text(1), M57V text(1), M57X decimal(2,0), M60 text(1), M61 decimal(4,0), M62 decimal(2,0), M65A text(1), M65B text(1), M65C text(1), M65D text(1), M65E text(1), M65F text(1), M65G text(1), M65H text(1), M65I text(1), M65J text(1), M65K text(1), M65L text(1), M65X text(1), M66 decimal(2,0), M70 decimal(2,0), M71 decimal(4,0), M72 decimal(3,0), M73 decimal(3,0)
RECH3.All (reader CSV_1)
    attributes: FileCode char(7), HHID char(6), SHDISTRICT number(2,0), SHUPAZILA number(3,0), SHADULT35 number(2,0), SHHTEC number(4,0), SH104A number(2,0), SH104B number(3,0), SH110G number(2,0), SH110H number(2,0), SH110I number(2,0), SH110J number(2,0), SH110K number(2,0), SH110L number(2,0), SH118A number(2,0), SH118B number(2,0), SH122A number(2,0), SH122C number(5,2)
    -> RECH3_All (writer MDB_ADO_1)
RECH3_All (writer MDB_ADO_1)
    attributes: FileCode text(7), HHID text(6), SHDISTRICT decimal(2,0), SHUPAZILA decimal(3,0), SHADULT35 decimal(2,0), SHHTEC decimal(4,0), SH104A decimal(2,0), SH104B decimal(3,0), SH110G decimal(2,0), SH110H decimal(2,0), SH110I decimal(2,0), SH110J decimal(2,0), SH110K decimal(2,0), SH110L decimal(2,0), SH118A decimal(2,0), SH118B decimal(2,0), SH122A decimal(2,0), SH122C decimal(5,2)
RECH4A.All (reader CSV_1)
    attributes: FileCode char(7), HHID char(6), IDXH4A number(3,0), SH6XA number(2,0), SH6XB number(2,0), SH6XC number(2,0), SH6XX number(2,0), SH6XY number(2,0), SH6XZ number(2,0), SH62A number(2,0), SH62B number(6,0), SH63 number(2,0), SH63B number(2,0), SH68A number(2,0), SH68B number(3,0), SH68C number(3,0), SH6YA number(2,0), SH6YB number(2,0), SH6YC number(2,0), SH6YD number(2,0), SH6YE number(2,0), SH6YF number(2,0), SH6YG number(2,0), SH6YH number(2,0), SH6YI number(2,0), SH6YJ number(2,0), SH6YX number(2,0), SH6YZ number(2,0), SH69A number(2,0), SH70 number(6,0),
      SH71 number(3,0), SH72 number(6,0), SH73 number(6,0), SH74 number(6,0), SH75 number(2,0), SH76 number(6,0), SH77A number(6,0), SH77B number(6,0), SH77C number(6,0), SH78 number(2,0), SH78A number(5,0), SH90 number(2,0), SH91 number(2,0), SH92 number(3,0), SH93 number(4,0), SH94 number(6,0), SH94A number(2,0), SH95 number(6,0), SH96A number(6,0), SH96B number(6,0), SH96C number(6,0)
    -> RECH4A_All (writer MDB_ADO_1)
RECH4A_All (writer MDB_ADO_1)
    attributes: FileCode text(7), HHID text(6), IDXH4A decimal(3,0), SH6XA decimal(2,0), SH6XB decimal(2,0), SH6XC decimal(2,0), SH6XX decimal(2,0), SH6XY decimal(2,0), SH6XZ decimal(2,0), SH62A decimal(2,0), SH62B decimal(6,0), SH63 decimal(2,0), SH63B decimal(2,0), SH68A decimal(2,0), SH68B decimal(3,0), SH68C decimal(3,0), SH6YA decimal(2,0), SH6YB decimal(2,0), SH6YC decimal(2,0), SH6YD decimal(2,0), SH6YE decimal(2,0), SH6YF decimal(2,0), SH6YG decimal(2,0), SH6YH decimal(2,0), SH6YI decimal(2,0), SH6YJ decimal(2,0), SH6YX decimal(2,0), SH6YZ decimal(2,0), SH69A decimal(2,0), SH70 decimal(6,0),
      SH71 decimal(3,0), SH72 decimal(6,0), SH73 decimal(6,0), SH74 decimal(6,0), SH75 decimal(2,0), SH76 decimal(6,0), SH77A decimal(6,0), SH77B decimal(6,0), SH77C decimal(6,0), SH78 decimal(2,0), SH78A decimal(5,0), SH90 decimal(2,0), SH91 decimal(2,0), SH92 decimal(3,0), SH93 decimal(4,0), SH94 decimal(6,0), SH94A decimal(2,0), SH95 decimal(6,0), SH96A decimal(6,0), SH96B decimal(6,0), SH96C decimal(6,0)
REC81.All (reader CSV_1)
    attributes: FileCode char(7), CASEID char(9), V801 number(5,0), V802 number(5,0), V803 number(3,0), V804 number(2,0), V805 number(4,0), V806 number(2,0), V811 number(2,0), V812 number(2,0), V813 number(2,0), V814 number(2,0), V815A char(1), V815B char(1), V815C char(1)
    -> REC81_All (writer MDB_ADO_1)
REC81_All (writer MDB_ADO_1)
    attributes: FileCode text(7), CASEID text(9), V801 decimal(5,0), V802 decimal(5,0), V803 decimal(3,0), V804 decimal(2,0), V805 decimal(4,0), V806 decimal(2,0), V811 decimal(2,0), V812 decimal(2,0), V813 decimal(2,0), V814 decimal(2,0), V815A text(1), V815B text(1), V815C text(1)
RECHG2.All (reader CSV_1)
    attributes: FileCode char(7), HHID char(7), SG101 number(3,0), SG103 number(3,0), SG104 number(2,0), SG105 number(2,0), SG106 number(2,0), SG107 number(2,0), SG108 number(3,0), SG109 number(2,0), SG110 number(4,0), SG111 number(3,0), SG112A number(7,0), SG112B number(2,0), SG113A number(6,0), SG113B number(6,0), SG113C number(6,0), SG113D number(6,0), SG114A number(7,0), SG114B number(7,0), SG115 number(2,0), SG116A number(3,0), SG116B number(3,0), SG116C number(3,0), SG116D number(3,0), SG117A number(7,0), SG117B number(2,0), SG118A number(7,0), SG118B number(2,0), SG119A number(7,0),
      SG119B number(2,0), SG120A char(1), SG120B char(1), SG121 number(2,0), SG122 number(2,0), SG123A number(2,0), SG123B number(2,0), SG123C number(2,0), SG123D number(2,0), SG123E number(2,0), SG123F number(2,0), SG123G number(2,0), SG123H number(2,0), SG123I number(2,0), SG123J number(2,0), SG123X number(2,0), SG124 number(2,0), SG125 number(2,0), SG126 number(7,0), SG127 number(3,0), SG128 number(2,0), SG129 number(2,0), SG201A number(2,0), SG201B number(2,0), SG201C number(2,0), SG201D number(2,0), SG201E number(2,0), SG201F number(2,0), SG201G number(2,0), SG201H number(2,0),
      SG201I number(2,0), SG201J number(2,0), SG201K number(2,0), SG201L number(2,0), SG201M number(2,0), SG201N number(2,0), SG201X number(2,0), SG202A number(2,0), SG202B number(2,0), SG202C number(2,0), SG202D number(2,0), SG202E number(2,0), SG202F number(2,0), SG202G number(2,0), SG202H number(2,0), SG202I number(2,0), SG202J number(2,0), SG202K number(2,0), SG202L number(2,0), SG202M char(1), SG202N char(1), SG202X number(2,0), SG203A number(2,0), SG203B number(3,0), SG204M number(3,0), SG204A number(5,0), SG205 number(3,0), SG206A number(2,0), SG206B number(6,0), SG207 number(3,0),
      SG207B number(2,0), SG208A number(2,0), SG208B number(7,0), SG209 number(2,0), SG210 number(2,0), SG211 number(2,0), SG213A number(2,0), SG213B number(7,0), SG214 number(2,0), SG215 number(2,0), SG216A number(2,0), SG216B number(2,0), SG216C number(2,0), SG216D number(2,0), SG216E number(2,0), SG216F number(2,0), SG216G number(2,0), SG216H number(2,0), SG216I number(2,0), SG216X number(2,0), SG216Z number(2,0), SG217A number(2,0), SG217B number(2,0), SG217C number(2,0), SG217D number(2,0), SG217E number(2,0), SG217F number(2,0), SG217G number(2,0), SG217H number(2,0), SG217I number(2,0),
      SG217X number(2,0), SG217Y number(2,0), SG217Z number(2,0), SG218 number(2,0), SG219A number(2,0), SG219B number(7,0), SG220 number(2,0), SG221 number(2,0), SG222A number(2,0), SG222B number(2,0), SG222C number(2,0), SG222D number(2,0), SG222E number(2,0), SG222F number(2,0), SG222G number(2,0), SG222H number(2,0), SG222I number(2,0), SG222J number(2,0), SG222K number(2,0), SG222X number(2,0), SG222Z number(2,0), SG223A number(2,0), SG223B number(2,0), SG223C number(2,0), SG223D number(2,0), SG223E number(2,0), SG223F number(2,0), SG223G number(2,0), SG223H number(2,0), SG223I number(2,0),
      SG223J number(2,0), SG223K number(2,0), SG223X number(2,0), SG223Y number(2,0), SG223Z number(2,0), SG224 number(2,0), SG225A number(2,0), SG225B number(7,0), SG226 number(2,0), SG227 number(6,0), SG228A number(2,0), SG228B number(2,0), SG228C number(2,0), SG228D number(2,0), SG228E number(2,0), SG228F number(2,0), SG228G number(2,0), SG228H number(2,0), SG228I number(2,0), SG228J number(2,0), SG228X number(2,0), SG228Y number(2,0), SG228Z number(2,0), SG229 number(3,0), SG230M number(3,0), SG230A number(5,0), SG231 number(3,0), SG232A number(2,0), SG232B number(6,0), SG233 number(2,0),
      SG234 number(2,0), SG235 number(2,0), SG237A number(2,0), SG237B number(6,0), SG238 number(2,0), SG239 number(2,0), SG240A number(2,0), SG240B number(2,0), SG240C number(2,0), SG240D number(2,0), SG240E number(2,0), SG240F number(2,0), SG240G number(2,0), SG240H number(2,0), SG240I number(2,0), SG240X number(2,0), SG240Z number(2,0), SG241A number(2,0), SG241B number(2,0), SG241C number(2,0), SG241D number(2,0), SG241E number(2,0), SG241F number(2,0), SG241G number(2,0), SG241H number(2,0), SG241I number(2,0), SG241X number(2,0), SG241Y number(2,0), SG241Z number(2,0), SG242 number(2,0),
      SG243A number(2,0), SG243B number(7,0), SG244 number(2,0), SG245 number(2,0), SG246A number(2,0), SG246B number(2,0), SG246C number(2,0), SG246D number(2,0), SG246E number(2,0), SG246X number(2,0), SG246Z number(2,0), SG247A number(2,0), SG247B number(2,0), SG247C number(2,0), SG247D number(2,0), SG247E number(2,0), SG247X number(2,0), SG247Y number(2,0), SG247Z number(2,0), SG248 number(2,0), SG249A number(2,0), SG249B char(1), SG250 number(2,0), SG251 number(6,0), SG252 number(2,0), SG253A number(4,0), SG253B number(4,0), SG253C number(4,0), SG253 number(4,0), SG254 number(3,0),
      SG255 number(3,0), SG256A number(2,0), SG256B number(6,0), SG257 number(3,0), SG258A number(2,0), SG258B number(7,0), SG259 number(2,0), SG260 number(2,0), SG261 number(2,0), SG262A number(2,0), SG262B number(6,0), SG263 number(2,0), SG264 number(2,0), SG265A number(2,0), SG265B number(2,0), SG265C number(2,0), SG265D number(2,0), SG265E number(2,0), SG265F number(2,0), SG265G number(2,0), SG265H number(2,0), SG265I number(2,0), SG265X number(2,0), SG265Z number(2,0), SG265AA number(2,0), SG265AB number(2,0), SG265AC number(2,0), SG265AD number(2,0), SG265AE number(2,0), SG265AF number(2,0),
      SG265AG number(2,0), SG265AH number(2,0), SG265AI number(2,0), SG265AX number(2,0), SG265AY number(2,0), SG265AZ number(2,0), SG265BB number(2,0), SG266A number(2,0), SG266B number(5,0), SG267 number(2,0), SG268 number(2,0), SG269A number(2,0), SG269B number(2,0), SG269C number(2,0), SG269D number(2,0), SG269E number(2,0), SG269F number(2,0), SG269G number(2,0), SG269H number(2,0), SG269I number(2,0), SG269J number(2,0), SG269K number(2,0), SG269X number(2,0), SG269Z number(2,0), SG270A number(2,0), SG270B number(2,0), SG270C number(2,0), SG270D number(2,0), SG270E number(2,0), SG270F number(2,0),
      SG270G number(2,0), SG270H number(2,0), SG270I number(2,0), SG270J number(2,0), SG270K number(2,0), SG270X number(2,0), SG270Y number(2,0), SG270Z number(2,0), SG271 number(2,0), SG272A number(2,0), SG272B number(7,0), SG273 number(2,0), SG274 number(6,0), SG275 number(2,0), SG276 number(4,0), SG277 number(2,0), SG278 number(2,0), SG279U number(2,0), SG279N number(2,0), SG280A number(2,0), SG280B number(7,0), SG281 number(2,0), SG282A number(2,0), SG282B number(2,0), SG282C number(2,0), SG283 number(6,0), SG284 number(2,0), SG285 number(2,0), SG286 number(6,0), SG287 number(2,0),
      SG288 number(2,0), SG289 number(7,0), SG290 number(2,0), SG291 number(3,0), SG292 number(6,0), SG292A number(7,0), SG301A number(2,0), SG301B number(2,0), SG301C number(2,0), SG301D number(2,0), SG301E number(2,0), SG301F number(2,0), SG301G number(2,0), SG301H number(2,0), SG301X number(2,0), SG302 number(2,0), SG303A number(2,0), SG303B number(2,0), SG303C number(2,0), SG304A number(2,0), SG304B number(2,0), SG304C number(2,0), SG304D number(2,0), SG304E number(2,0), SG304X number(2,0), SG305 number(3,0), SG306 number(2,0), SG307 number(2,0), SG308 number(2,0), SG309 number(2,0),
      SG310 number(2,0), SG311 number(3,0), SINGRESOO number(8,0), SINGRESOE number(7,0), SREGALIAP number(7,0), SBONIFICA number(7,0), SIFUENTE1 number(8,0), SIFUENTE2 number(7,0), SIFUENTE3 number(7,0), SIFUENTE4 char(1), SINGRESOTP number(8,0), SINGRESOIP number(2,0), SINGRESOIB number(3,0), SGASTOTI char(1), SINGRESOIPA number(2,0)
    -> RECHG2_All (writer MDB_ADO_1)
RECHG2_All (writer MDB_ADO_1)
    attributes: FileCode text(7), HHID text(7), SG101 decimal(3,0), SG103 decimal(3,0), SG104 decimal(2,0), SG105 decimal(2,0), SG106 decimal(2,0), SG107 decimal(2,0), SG108 decimal(3,0), SG109 decimal(2,0), SG110 decimal(4,0), SG111 decimal(3,0), SG112A decimal(7,0), SG112B decimal(2,0), SG113A decimal(6,0), SG113B decimal(6,0), SG113C decimal(6,0), SG113D decimal(6,0), SG114A decimal(7,0), SG114B decimal(7,0), SG115 decimal(2,0), SG116A decimal(3,0), SG116B decimal(3,0), SG116C decimal(3,0), SG116D decimal(3,0), SG117A decimal(7,0), SG117B decimal(2,0), SG118A decimal(7,0), SG118B decimal(2,0), SG119A decimal(7,0),
      SG119B decimal(2,0), SG120A text(1), SG120B text(1), SG121 decimal(2,0), SG122 decimal(2,0), SG123A decimal(2,0), SG123B decimal(2,0), SG123C decimal(2,0), SG123D decimal(2,0), SG123E decimal(2,0), SG123F decimal(2,0), SG123G decimal(2,0), SG123H decimal(2,0), SG123I decimal(2,0), SG123J decimal(2,0), SG123X decimal(2,0), SG124 decimal(2,0), SG125 decimal(2,0), SG126 decimal(7,0), SG127 decimal(3,0), SG128 decimal(2,0), SG129 decimal(2,0), SG201A decimal(2,0), SG201B decimal(2,0), SG201C decimal(2,0), SG201D decimal(2,0), SG201E decimal(2,0), SG201F decimal(2,0), SG201G decimal(2,0), SG201H decimal(2,0),
      SG201I decimal(2,0), SG201J decimal(2,0), SG201K decimal(2,0), SG201L decimal(2,0), SG201M decimal(2,0), SG201N decimal(2,0), SG201X decimal(2,0), SG202A decimal(2,0), SG202B decimal(2,0), SG202C decimal(2,0), SG202D decimal(2,0), SG202E decimal(2,0), SG202F decimal(2,0), SG202G decimal(2,0), SG202H decimal(2,0), SG202I decimal(2,0), SG202J decimal(2,0), SG202K decimal(2,0), SG202L decimal(2,0), SG202M text(1), SG202N text(1), SG202X decimal(2,0), SG203A decimal(2,0), SG203B decimal(3,0), SG204M decimal(3,0), SG204A decimal(5,0), SG205 decimal(3,0), SG206A decimal(2,0), SG206B decimal(6,0), SG207 decimal(3,0),
      SG207B decimal(2,0), SG208A decimal(2,0), SG208B decimal(7,0), SG209 decimal(2,0), SG210 decimal(2,0), SG211 decimal(2,0), SG213A decimal(2,0), SG213B decimal(7,0), SG214 decimal(2,0), SG215 decimal(2,0), SG216A decimal(2,0), SG216B decimal(2,0), SG216C decimal(2,0), SG216D decimal(2,0), SG216E decimal(2,0), SG216F decimal(2,0), SG216G decimal(2,0), SG216H decimal(2,0), SG216I decimal(2,0), SG216X decimal(2,0), SG216Z decimal(2,0), SG217A decimal(2,0), SG217B decimal(2,0), SG217C decimal(2,0), SG217D decimal(2,0), SG217E decimal(2,0), SG217F decimal(2,0), SG217G decimal(2,0), SG217H decimal(2,0), SG217I decimal(2,0),
      SG217X decimal(2,0), SG217Y decimal(2,0), SG217Z decimal(2,0), SG218 decimal(2,0), SG219A decimal(2,0), SG219B decimal(7,0), SG220 decimal(2,0), SG221 decimal(2,0), SG222A decimal(2,0), SG222B decimal(2,0), SG222C decimal(2,0), SG222D decimal(2,0), SG222E decimal(2,0), SG222F decimal(2,0), SG222G decimal(2,0), SG222H decimal(2,0), SG222I decimal(2,0), SG222J decimal(2,0), SG222K decimal(2,0), SG222X decimal(2,0), SG222Z decimal(2,0), SG223A decimal(2,0), SG223B decimal(2,0), SG223C decimal(2,0), SG223D decimal(2,0), SG223E decimal(2,0), SG223F decimal(2,0), SG223G decimal(2,0), SG223H decimal(2,0), SG223I decimal(2,0),
      SG223J decimal(2,0), SG223K decimal(2,0), SG223X decimal(2,0), SG223Y decimal(2,0), SG223Z decimal(2,0), SG224 decimal(2,0), SG225A decimal(2,0), SG225B decimal(7,0), SG226 decimal(2,0), SG227 decimal(6,0), SG228A decimal(2,0), SG228B decimal(2,0), SG228C decimal(2,0), SG228D decimal(2,0), SG228E decimal(2,0), SG228F decimal(2,0), SG228G decimal(2,0), SG228H decimal(2,0), SG228I decimal(2,0), SG228J decimal(2,0), SG228X decimal(2,0), SG228Y decimal(2,0), SG228Z decimal(2,0), SG229 decimal(3,0), SG230M decimal(3,0), SG230A decimal(5,0), SG231 decimal(3,0), SG232A decimal(2,0), SG232B decimal(6,0), SG233 decimal(2,0),
      SG234 decimal(2,0), SG235 decimal(2,0), SG237A decimal(2,0), SG237B decimal(6,0), SG238 decimal(2,0), SG239 decimal(2,0), SG240A decimal(2,0), SG240B decimal(2,0), SG240C decimal(2,0), SG240D decimal(2,0), SG240E decimal(2,0), SG240F decimal(2,0), SG240G decimal(2,0), SG240H decimal(2,0), SG240I decimal(2,0), SG240X decimal(2,0), SG240Z decimal(2,0), SG241A decimal(2,0), SG241B decimal(2,0), SG241C decimal(2,0), SG241D decimal(2,0), SG241E decimal(2,0), SG241F decimal(2,0), SG241G decimal(2,0), SG241H decimal(2,0), SG241I decimal(2,0), SG241X decimal(2,0), SG241Y decimal(2,0), SG241Z decimal(2,0), SG242 decimal(2,0),
      SG243A decimal(2,0), SG243B decimal(7,0), SG244 decimal(2,0), SG245 decimal(2,0), SG246A decimal(2,0), SG246B decimal(2,0), SG246C decimal(2,0), SG246D decimal(2,0), SG246E decimal(2,0), SG246X decimal(2,0), SG246Z decimal(2,0), SG247A decimal(2,0), SG247B decimal(2,0), SG247C decimal(2,0), SG247D decimal(2,0), SG247E decimal(2,0), SG247X decimal(2,0), SG247Y decimal(2,0), SG247Z decimal(2,0), SG248 decimal(2,0), SG249A decimal(2,0), SG249B text(1), SG250 decimal(2,0), SG251 decimal(6,0), SG252 decimal(2,0), SG253A decimal(4,0), SG253B decimal(4,0), SG253C decimal(4,0), SG253 decimal(4,0), SG254 decimal(3,0),
      SG255 decimal(3,0), SG256A decimal(2,0), SG256B decimal(6,0), SG257 decimal(3,0), SG258A decimal(2,0), SG258B decimal(7,0), SG259 decimal(2,0), SG260 decimal(2,0), SG261 decimal(2,0), SG262A decimal(2,0), SG262B decimal(6,0), SG263 decimal(2,0), SG264 decimal(2,0), SG265A decimal(2,0), SG265B decimal(2,0), SG265C decimal(2,0), SG265D decimal(2,0), SG265E decimal(2,0), SG265F decimal(2,0), SG265G decimal(2,0), SG265H decimal(2,0), SG265I decimal(2,0), SG265X decimal(2,0), SG265Z decimal(2,0), SG265AA decimal(2,0), SG265AB decimal(2,0), SG265AC decimal(2,0), SG265AD decimal(2,0), SG265AE decimal(2,0), SG265AF decimal(2,0),
      SG265AG decimal(2,0), SG265AH decimal(2,0), SG265AI decimal(2,0), SG265AX decimal(2,0), SG265AY decimal(2,0), SG265AZ decimal(2,0), SG265BB decimal(2,0), SG266A decimal(2,0), SG266B decimal(5,0), SG267 decimal(2,0), SG268 decimal(2,0), SG269A decimal(2,0), SG269B decimal(2,0), SG269C decimal(2,0), SG269D decimal(2,0), SG269E decimal(2,0), SG269F decimal(2,0), SG269G decimal(2,0), SG269H decimal(2,0), SG269I decimal(2,0), SG269J decimal(2,0), SG269K decimal(2,0), SG269X decimal(2,0), SG269Z decimal(2,0), SG270A decimal(2,0), SG270B decimal(2,0), SG270C decimal(2,0), SG270D decimal(2,0), SG270E decimal(2,0), SG270F decimal(2,0),
      SG270G decimal(2,0), SG270H decimal(2,0), SG270I decimal(2,0), SG270J decimal(2,0), SG270K decimal(2,0), SG270X decimal(2,0), SG270Y decimal(2,0), SG270Z decimal(2,0), SG271 decimal(2,0), SG272A decimal(2,0), SG272B decimal(7,0), SG273 decimal(2,0), SG274 decimal(6,0), SG275 decimal(2,0), SG276 decimal(4,0), SG277 decimal(2,0), SG278 decimal(2,0), SG279U decimal(2,0), SG279N decimal(2,0), SG280A decimal(2,0), SG280B decimal(7,0), SG281 decimal(2,0), SG282A decimal(2,0), SG282B decimal(2,0), SG282C decimal(2,0), SG283 decimal(6,0), SG284 decimal(2,0), SG285 decimal(2,0), SG286 decimal(6,0), SG287 decimal(2,0),
      SG288 decimal(2,0), SG289 decimal(7,0), SG290 decimal(2,0), SG291 decimal(3,0), SG292 decimal(6,0), SG292A decimal(7,0), SG301A decimal(2,0), SG301B decimal(2,0), SG301C decimal(2,0), SG301D decimal(2,0), SG301E decimal(2,0), SG301F decimal(2,0), SG301G decimal(2,0), SG301H decimal(2,0), SG301X decimal(2,0), SG302 decimal(2,0), SG303A decimal(2,0), SG303B decimal(2,0), SG303C decimal(2,0), SG304A decimal(2,0), SG304B decimal(2,0), SG304C decimal(2,0), SG304D decimal(2,0), SG304E decimal(2,0), SG304X decimal(2,0), SG305 decimal(3,0), SG306 decimal(2,0), SG307 decimal(2,0), SG308 decimal(2,0), SG309 decimal(2,0),
      SG310 decimal(2,0), SG311 decimal(3,0), SINGRESOO decimal(8,0), SINGRESOE decimal(7,0), SREGALIAP decimal(7,0), SBONIFICA decimal(7,0), SIFUENTE1 decimal(8,0), SIFUENTE2 decimal(7,0), SIFUENTE3 decimal(7,0), SIFUENTE4 text(1), SINGRESOTP decimal(8,0), SINGRESOIP decimal(2,0), SINGRESOIB decimal(3,0), SGASTOTI text(1), SINGRESOIPA decimal(2,0)
RECHMA.All (reader CSV_1)
    attributes: FileCode char(7), HHID char(7), HB0 number(3,0), HB1 number(3,0), HB2 number(5,0), HB3 number(5,0), HB4 number(5,0), HB5 number(5,0), HB6 number(6,0), HB11 number(5,0), HB12 number(6,0), HB12A number(6,0), HB12B number(6,0), HB13 number(2,0), HB32 number(5,0), HB33 number(2,0), HB35 char(1), HB40 number(5,0), HB41 number(5,0), HB50 char(1), HB51 char(1), HB52 char(1), HB53 char(1), HB55 char(1), HB56 char(1), HB57 char(1), HB58 char(1), HB60 char(1), HB61 char(1), HB62 char(1),
      HB63 char(1), HB64 char(1), HB65 number(2,0), HB66 number(2,0), HB67 number(3,0), HB68 number(2,0), HB69 char(1), HB70 char(1)
    -> RECHMA_All (writer MDB_ADO_1)
RECHMA_All (writer MDB_ADO_1)
    attributes: FileCode text(7), HHID text(7), HB0 decimal(3,0), HB1 decimal(3,0), HB2 decimal(5,0), HB3 decimal(5,0), HB4 decimal(5,0), HB5 decimal(5,0), HB6 decimal(6,0), HB11 decimal(5,0), HB12 decimal(6,0), HB12A decimal(6,0), HB12B decimal(6,0), HB13 decimal(2,0), HB32 decimal(5,0), HB33 decimal(2,0), HB35 text(1), HB40 decimal(5,0), HB41 decimal(5,0), HB50 text(1), HB51 text(1), HB52 text(1), HB53 text(1), HB55 text(1), HB56 text(1), HB57 text(1), HB58 text(1), HB60 text(1), HB61 text(1), HB62 text(1),
      HB63 text(1), HB64 text(1), HB65 decimal(2,0), HB66 decimal(2,0), HB67 decimal(3,0), HB68 decimal(2,0), HB69 text(1), HB70 text(1)
RECHMT.All (reader CSV_1)
    attributes: FileCode char(7), HHID char(7), SHMTX number(2,0), SH78 number(2,0), SH79 number(3,0), SH80M number(3,0), SH80A number(5,0), SH81 number(2,0), SH80MI number(3,0), SH80AI number(5,0), SH80C number(3,0)
    -> RECHMT_All (writer MDB_ADO_1)
RECHMT_All (writer MDB_ADO_1)
    attributes: FileCode text(7), HHID text(7), SHMTX decimal(2,0), SH78 decimal(2,0), SH79 decimal(3,0), SH80M decimal(3,0), SH80A decimal(5,0), SH81 decimal(2,0), SH80MI decimal(3,0), SH80AI decimal(5,0), SH80C decimal(3,0)
REC98.All (reader CSV_1)
    attributes: FileCode char(7), CASEID char(11), IDX98 number(2,0), S570 number(3,0), S571 number(3,0), S572 number(3,0), S573A number(2,0), S573B number(9,0), S573C number(3,0), S573D number(3,0), S573E number(5,0), S575 number(9,0), S576A number(3,0), S576B number(3,0), S576C number(5,0), S576D number(9,0), S576E number(3,0), S576F number(3,0), S576G number(5,0), S576H number(9,0), S576I number(3,0), S576J number(3,0), S577A number(5,0), S577B number(9,0), S577C number(3,0), S577D number(3,0), S577E number(5,0), S577F number(9,0), S577G number(3,0), S577G1 number(3,0),
      S577G2 number(5,0), S577H number(9,0), S577I number(3,0), S577J number(3,0), S577K number(5,0), S577L number(9,0), S577M number(3,0), S577N number(3,0), S577O number(5,0), S577P number(9,0), S577Q number(3,0), S577R number(3,0), S578A number(5,0), S578B number(9,0), S578C number(3,0), S578D number(3,0), S578E number(5,0), S578F number(9,0), S578G number(3,0), S578H number(3,0), S578I number(5,0), S578J number(9,0), S578K number(3,0), S578L number(3,0), S578M number(5,0), S578N number(9,0), S578O number(3,0), S578P number(3,0), S578P1 number(5,0), S578P2 number(9,0),
      S578Q number(3,0), S578R number(3,0), S578S number(5,0), S578T number(9,0), S578U number(3,0), S578V number(3,0), S578W number(5,0), S578X number(9,0), S578Y number(3,0), S579A number(3,0), S579B number(5,0), S579C number(9,0), S579D number(3,0), S579E number(3,0), S579F number(5,0), S579G number(2,0), S580 number(2,0), S581A number(2,0), S581B number(2,0), S581C number(2,0), S581D number(2,0), S581E number(2,0), S581F number(2,0), S581G number(2,0), S581H number(2,0), S581I number(2,0), S581J number(2,0), S581X number(2,0), S582 number(2,0), S583 number(3,0),
      S583B number(3,0), S584 number(3,0), S584B number(3,0), S585 number(2,0), S586 number(2,0), S587 number(3,0), S588 number(2,0), S589 number(3,0), S591 number(3,0)
    -> REC98_All (writer MDB_ADO_1)
REC98_All (writer MDB_ADO_1)
    attributes: FileCode text(7), CASEID text(11), IDX98 decimal(2,0), S570 decimal(3,0), S571 decimal(3,0), S572 decimal(3,0), S573A decimal(2,0), S573B decimal(9,0), S573C decimal(3,0), S573D decimal(3,0), S573E decimal(5,0), S575 decimal(9,0), S576A decimal(3,0), S576B decimal(3,0), S576C decimal(5,0), S576D decimal(9,0), S576E decimal(3,0), S576F decimal(3,0), S576G decimal(5,0), S576H decimal(9,0), S576I decimal(3,0), S576J decimal(3,0), S577A decimal(5,0), S577B decimal(9,0), S577C decimal(3,0), S577D decimal(3,0), S577E decimal(5,0), S577F decimal(9,0), S577G decimal(3,0), S577G1 decimal(3,0),
      S577G2 decimal(5,0), S577H decimal(9,0), S577I decimal(3,0), S577J decimal(3,0), S577K decimal(5,0), S577L decimal(9,0), S577M decimal(3,0), S577N decimal(3,0), S577O decimal(5,0), S577P decimal(9,0), S577Q decimal(3,0), S577R decimal(3,0), S578A decimal(5,0), S578B decimal(9,0), S578C decimal(3,0), S578D decimal(3,0), S578E decimal(5,0), S578F decimal(9,0), S578G decimal(3,0), S578H decimal(3,0), S578I decimal(5,0), S578J decimal(9,0), S578K decimal(3,0), S578L decimal(3,0), S578M decimal(5,0), S578N decimal(9,0), S578O decimal(3,0), S578P decimal(3,0), S578P1 decimal(5,0), S578P2 decimal(9,0),
      S578Q decimal(3,0), S578R decimal(3,0), S578S decimal(5,0), S578T decimal(9,0), S578U decimal(3,0), S578V decimal(3,0), S578W decimal(5,0), S578X decimal(9,0), S578Y decimal(3,0), S579A decimal(3,0), S579B decimal(5,0), S579C decimal(9,0), S579D decimal(3,0), S579E decimal(3,0), S579F decimal(5,0), S579G decimal(2,0), S580 decimal(2,0), S581A decimal(2,0), S581B decimal(2,0), S581C decimal(2,0), S581D decimal(2,0), S581E decimal(2,0), S581F decimal(2,0), S581G decimal(2,0), S581H decimal(2,0), S581I decimal(2,0), S581J decimal(2,0), S581X decimal(2,0), S582 decimal(2,0), S583 decimal(3,0),
      S583B decimal(3,0), S584 decimal(3,0), S584B decimal(3,0), S585 decimal(2,0), S586 decimal(2,0), S587 decimal(3,0), S588 decimal(2,0), S589 decimal(3,0), S591 decimal(3,0)
RECH2.All (reader CSV_1)
    attributes: FileCode char(7), HHID char(6), HV201 number(3,0), HV202 char(1), HV204 number(4,0), HV205 number(3,0), HV206 number(2,0), HV207 number(2,0), HV208 number(2,0), HV209 number(2,0), HV210 number(2,0), HV211 number(2,0), HV212 char(1), HV213 number(3,0), HV214 number(3,0), HV215 number(3,0), HV216 number(3,0), HV217 number(2,0), HV218 number(2,0), HV219 number(2,0), HV220 number(3,0), HV221 number(2,0), HV225 number(2,0), HV226 number(3,0), HV227 char(1), HV228 char(1), HV230A number(2,0), HV230B number(2,0), HV232 number(2,0), HV232B number(2,0),
      HV232C number(2,0), HV232D number(2,0), HV232E char(1), HV232Y number(2,0), HV234 char(1), HV234A number(2,0), HV235 number(2,0), HV236 char(1), HV237 number(2,0), HV237A number(2,0), HV237B number(2,0), HV237C number(2,0), HV237D number(2,0), HV237E number(2,0), HV237F number(2,0), HV237G number(2,0), HV237H char(1), HV237I char(1), HV237J char(1), HV237K char(1), HV237X number(2,0), HV237Z number(2,0), HV238 number(3,0), HV239 char(1), HV240 char(1), HV241 number(2,0), HV242 number(2,0), HV243A number(2,0), HV243B char(1), HV243C char(1),
      HV243D char(1), HV244 number(2,0), HV245 number(4,0), HV246 number(2,0), HV246A char(1), HV246B number(2,0), HV246C char(1), HV246D char(1), HV246E char(1), HV246F char(1), HV246G number(3,0), HV246H number(3,0), HV246I number(3,0), HV246J char(1), HV246K char(1), HV247 number(2,0), HV252 number(2,0), HV253 char(1), HV253A char(1), HV253B char(1), HV253C char(1), HV253D char(1), HV253E char(1), HV253F char(1), HV253G char(1), HV253H char(1), HV253X char(1), HV253Z char(1), HV270 number(2,0), HV271 number(8,0),
      HML1 char(1), HML1A char(1), HML2 char(1)
    -> RECH2_All (writer MDB_ADO_1)
RECH2_All (writer MDB_ADO_1)
    attributes: FileCode text(7), HHID text(6), HV201 decimal(3,0), HV202 text(1), HV204 decimal(4,0), HV205 decimal(3,0), HV206 decimal(2,0), HV207 decimal(2,0), HV208 decimal(2,0), HV209 decimal(2,0), HV210 decimal(2,0), HV211 decimal(2,0), HV212 text(1), HV213 decimal(3,0), HV214 decimal(3,0), HV215 decimal(3,0), HV216 decimal(3,0), HV217 decimal(2,0), HV218 decimal(2,0), HV219 decimal(2,0), HV220 decimal(3,0), HV221 decimal(2,0), HV225 decimal(2,0), HV226 decimal(3,0), HV227 text(1), HV228 text(1), HV230A decimal(2,0), HV230B decimal(2,0), HV232 decimal(2,0), HV232B decimal(2,0),
      HV232C decimal(2,0), HV232D decimal(2,0), HV232E text(1), HV232Y decimal(2,0), HV234 text(1), HV234A decimal(2,0), HV235 decimal(2,0), HV236 text(1), HV237 decimal(2,0), HV237A decimal(2,0), HV237B decimal(2,0), HV237C decimal(2,0), HV237D decimal(2,0), HV237E decimal(2,0), HV237F decimal(2,0), HV237G decimal(2,0), HV237H text(1), HV237I text(1), HV237J text(1), HV237K text(1), HV237X decimal(2,0), HV237Z decimal(2,0), HV238 decimal(3,0), HV239 text(1), HV240 text(1), HV241 decimal(2,0), HV242 decimal(2,0), HV243A decimal(2,0), HV243B text(1), HV243C text(1),
      HV243D text(1), HV244 decimal(2,0), HV245 decimal(4,0), HV246 decimal(2,0), HV246A text(1), HV246B decimal(2,0), HV246C text(1), HV246D text(1), HV246E text(1), HV246F text(1), HV246G decimal(3,0), HV246H decimal(3,0), HV246I decimal(3,0), HV246J text(1), HV246K text(1), HV247 decimal(2,0), HV252 decimal(2,0), HV253 text(1), HV253A text(1), HV253B text(1), HV253C text(1), HV253D text(1), HV253E text(1), HV253F text(1), HV253G text(1), HV253H text(1), HV253X text(1), HV253Z text(1), HV270 decimal(2,0), HV271 decimal(8,0),
      HML1 text(1), HML1A text(1), HML2 text(1)
RECHPC.All (reader CSV_1)
    attributes: FileCode char(7), HHID char(6), HPCIDX number(3,0), SH198C number(2,0), SH198D number(2,0)
    -> RECHPC_All (writer MDB_ADO_1)
RECHPC_All (writer MDB_ADO_1)
    attributes: FileCode text(7), HHID text(6), HPCIDX decimal(3,0), SH198C decimal(2,0), SH198D decimal(2,0)
REC32.All (reader CSV_1)
    attributes: FileCode char(7), CASEID char(9), V310 char(1), V311 char(1), V312 number(3,0), V313 number(2,0), V315 number(3,0), V316 number(5,0), V317 number(5,0), V318 number(2,0), V319 number(2,0), V320 number(2,0), V321 number(2,0), V322 number(2,0), V323 number(3,0), V323A number(3,0), V325A char(1), V326 number(3,0), V327 number(2,0), V337 number(3,0), V359 number(3,0), V360 number(3,0), V361 number(2,0), V362 number(2,0), V363 number(3,0), V364 number(2,0), V367 number(2,0), V372 number(2,0), V372A number(2,0), V375A char(1),
      V376 number(3,0), V376A char(1), V379 char(1), V380 char(1), V384A number(2,0), V384B number(2,0), V384C number(2,0), V393 char(1), V394 char(1), V395 char(1), V3A00A number(2,0), V3A00B number(2,0), V3A00C number(2,0), V3A00D number(2,0), V3A00E number(2,0), V3A00F number(2,0), V3A00G number(2,0), V3A00H number(2,0), V3A00I number(2,0), V3A00J number(2,0), V3A00K number(2,0), V3A00L number(2,0), V3A00M number(2,0), V3A00N number(2,0), V3A00O number(2,0), V3A00P char(1), V3A00Q char(1), V3A00R char(1), V3A00S number(2,0), V3A00T char(1),
      V3A00U number(2,0), V3A00V number(2,0), V3A00W number(2,0), V3A00X number(2,0), V3A00Y number(2,0), V3A00Z number(2,0), V3A01 char(1), V3A02 char(1), V3A03 char(1), V3A04 char(1), V3A05 char(1), V3A06 char(1), V3A07 number(3,0), V3A08A char(1), V3A08B number(2,0), V3A08C number(2,0), V3A08D number(2,0), V3A08E number(2,0), V3A08F number(2,0), V3A08G number(2,0), V3A08H number(2,0), V3A08I number(2,0), V3A08J number(2,0), V3A08K number(2,0), V3A08L number(2,0), V3A08M number(2,0), V3A08N number(2,0), V3A08O char(1), V3A08P number(2,0), V3A08Q number(2,0),
      V3A08R number(2,0), V3A08S number(2,0), V3A08T number(2,0), V3A08U number(2,0), V3A08V number(2,0), V3A08W char(1), V3A08AA char(1), V3A08AB char(1), V3A08AC char(1), V3A08AD char(1), V3A08X number(2,0), V3A08Z number(2,0), V3A09A char(1), V3A09B char(1)
    -> REC32_All (writer MDB_ADO_1)
REC32_All (writer MDB_ADO_1)
    attributes: FileCode text(7), CASEID text(9), V310 text(1), V311 text(1), V312 decimal(3,0), V313 decimal(2,0), V315 decimal(3,0), V316 decimal(5,0), V317 decimal(5,0), V318 decimal(2,0), V319 decimal(2,0), V320 decimal(2,0), V321 decimal(2,0), V322 decimal(2,0), V323 decimal(3,0), V323A decimal(3,0), V325A text(1), V326 decimal(3,0), V327 decimal(2,0), V337 decimal(3,0), V359 decimal(3,0), V360 decimal(3,0), V361 decimal(2,0), V362 decimal(2,0), V363 decimal(3,0), V364 decimal(2,0), V367 decimal(2,0), V372 decimal(2,0), V372A decimal(2,0), V375A text(1),
      V376 decimal(3,0), V376A text(1), V379 text(1), V380 text(1), V384A decimal(2,0), V384B decimal(2,0), V384C decimal(2,0), V393 text(1), V394 text(1), V395 text(1), V3A00A decimal(2,0), V3A00B decimal(2,0), V3A00C decimal(2,0), V3A00D decimal(2,0), V3A00E decimal(2,0), V3A00F decimal(2,0), V3A00G decimal(2,0), V3A00H decimal(2,0), V3A00I decimal(2,0), V3A00J decimal(2,0), V3A00K decimal(2,0), V3A00L decimal(2,0), V3A00M decimal(2,0), V3A00N decimal(2,0), V3A00O decimal(2,0), V3A00P text(1), V3A00Q text(1), V3A00R text(1), V3A00S decimal(2,0), V3A00T text(1),
      V3A00U decimal(2,0), V3A00V decimal(2,0), V3A00W decimal(2,0), V3A00X decimal(2,0), V3A00Y decimal(2,0), V3A00Z decimal(2,0), V3A01 text(1), V3A02 text(1), V3A03 text(1), V3A04 text(1), V3A05 text(1), V3A06 text(1), V3A07 decimal(3,0), V3A08A text(1), V3A08B decimal(2,0), V3A08C decimal(2,0), V3A08D decimal(2,0), V3A08E decimal(2,0), V3A08F decimal(2,0), V3A08G decimal(2,0), V3A08H decimal(2,0), V3A08I decimal(2,0), V3A08J decimal(2,0), V3A08K decimal(2,0), V3A08L decimal(2,0), V3A08M decimal(2,0), V3A08N decimal(2,0), V3A08O text(1), V3A08P decimal(2,0), V3A08Q decimal(2,0),
      V3A08R decimal(2,0), V3A08S decimal(2,0), V3A08T decimal(2,0), V3A08U decimal(2,0), V3A08V decimal(2,0), V3A08W text(1), V3A08AA text(1), V3A08AB text(1), V3A08AC text(1), V3A08AD text(1), V3A08X decimal(2,0), V3A08Z decimal(2,0), V3A09A text(1), V3A09B text(1)
REC80.All (reader CSV_1)
    attributes: FileCode char(7), CASEID char(9), V820 char(1), V821A char(1), V821B char(1), V821C char(1), V822 char(1), V823 number(2,0), V824 char(1), V825 char(1), V826 char(1), V826A char(1), V827 char(1), V828 char(1), V829 char(1), V830 char(1), V831 char(1), V832B char(1), V832C char(1), V833A char(1), V833B char(1), V833C char(1), V834A char(1), V834B char(1), V834C char(1), V835A char(1), V835B char(1), V835C char(1), V836 char(1), V837 char(1),
      V838A char(1), V838B char(1), V838C char(1), V839 char(1), V839A char(1), V840 char(1), V840A char(1), V841 char(1), V841A char(1), V842 char(1), V843 char(1), V844 char(1), V845 char(1), V846 char(1), V847 char(1), V848 char(1), V849 char(1), V850A char(1), V850B char(1), V851A char(1), V851B char(1), V851C char(1), V851D char(1), V851E char(1), V851F char(1), V851G char(1), V851H char(1), V851I char(1), V851J char(1), V851K char(1),
      V851L char(1), V852A char(1), V852B char(1), V852C char(1), V853A char(1), V853B char(1), V853C char(1), V854A char(1), V854B char(1), V855 char(1)
    -> REC80_All (writer MDB_ADO_1)
REC80_All (writer MDB_ADO_1)
    attributes: FileCode text(7), CASEID text(9), V820 text(1), V821A text(1), V821B text(1), V821C text(1), V822 text(1), V823 decimal(2,0), V824 text(1), V825 text(1), V826 text(1), V826A text(1), V827 text(1), V828 text(1), V829 text(1), V830 text(1), V831 text(1), V832B text(1), V832C text(1), V833A text(1), V833B text(1), V833C text(1), V834A text(1), V834B text(1), V834C text(1), V835A text(1), V835B text(1), V835C text(1), V836 text(1), V837 text(1),
      V838A text(1), V838B text(1), V838C text(1), V839 text(1), V839A text(1), V840 text(1), V840A text(1), V841 text(1), V841A text(1), V842 text(1), V843 text(1), V844 text(1), V845 text(1), V846 text(1), V847 text(1), V848 text(1), V849 text(1), V850A text(1), V850B text(1), V851A text(1), V851B text(1), V851C text(1), V851D text(1), V851E text(1), V851F text(1), V851G text(1), V851H text(1), V851I text(1), V851J text(1), V851K text(1),
      V851L text(1), V852A text(1), V852B text(1), V852C text(1), V853A text(1), V853B text(1), V853C text(1), V854A text(1), V854B text(1), V855 text(1)
RECHG1.All (reader CSV_1)
    attributes: FileCode char(7), HHID char(7), SGCONGL number(5,0), SGHOGAR number(3,0), SGESTR char(1), SGPROVIN number(2,0), SGMUNIC char(1), SGZONA number(2,0), SGRESP number(3,0), SGINT number(9,0), SGINTD number(3,0), SGINTM number(3,0), SGINTA number(5,0), SGINTNUM number(4,0), SGRESULT number(2,0), SGVISITS number(2,0), SGSUPERV number(4,0), SGEDITC number(4,0), SGEDITO number(2,0), SGDIGIT number(3,0), SGHORAI number(3,0), SGMINUTI number(3,0), SGHORAF number(3,0), SGMINUTF number(3,0), SGWEIGHT number(9,0), SINGRTH number(8,0), SINGRTHP number(9,0), SINGRHI number(2,0), SVIVIG1 number(2,0), SVIVIG2 number(2,0),
      SVALPRO number(6,0), SQUINTIP number(2,0), SALLINCI number(2,0)
    -> RECHG1_All (writer MDB_ADO_1)
RECHG1_All (writer MDB_ADO_1)
    attributes: FileCode text(7), HHID text(7), SGCONGL decimal(5,0), SGHOGAR decimal(3,0), SGESTR text(1), SGPROVIN decimal(2,0), SGMUNIC text(1), SGZONA decimal(2,0), SGRESP decimal(3,0), SGINT decimal(9,0), SGINTD decimal(3,0), SGINTM decimal(3,0), SGINTA decimal(5,0), SGINTNUM decimal(4,0), SGRESULT decimal(2,0), SGVISITS decimal(2,0), SGSUPERV decimal(4,0), SGEDITC decimal(4,0), SGEDITO decimal(2,0), SGDIGIT decimal(3,0), SGHORAI decimal(3,0), SGMINUTI decimal(3,0), SGHORAF decimal(3,0), SGMINUTF decimal(3,0), SGWEIGHT decimal(9,0), SINGRTH decimal(8,0), SINGRTHP decimal(9,0), SINGRHI decimal(2,0), SVIVIG1 decimal(2,0), SVIVIG2 decimal(2,0),
      SVALPRO decimal(6,0), SQUINTIP decimal(2,0), SALLINCI decimal(2,0)
REC97.All (reader CSV_1)
    attributes: FileCode char(7), CASEID char(12), S902 number(2,0), S903A number(2,0), S903B number(2,0), S903C number(2,0), S903D number(2,0), S903E number(2,0), S903F number(2,0), S903G number(2,0), S903H number(2,0), S903X number(2,0), S903Z number(2,0), S904 number(2,0), S905M number(3,0), S905Y number(5,0), S906 number(2,0), S907 number(2,0), S908 number(3,0), S909 number(2,0), S910 number(2,0), S911 number(2,0), S912 number(2,0), S913 number(3,0), S914 number(2,0), S915 number(3,0), S916 number(2,0), S917 number(3,0), S918 number(2,0), S919 number(3,0),
      S920 number(2,0), S921 number(2,0), S922 number(2,0), S923 number(2,0), S924 number(3,0), S926 number(2,0), S927 number(2,0), S928 number(2,0), S929 number(2,0), S930 number(3,0), S931 number(2,0), S932 number(2,0), S933 number(2,0), S934 number(2,0), S936 number(2,0), S937A number(2,0), S937B number(2,0), S937C number(2,0), S937D number(2,0), S937E number(2,0), S937F number(2,0), S937G number(2,0), S937H number(2,0), S937X number(2,0), S937Z number(2,0), S938 number(2,0), S939 number(2,0), S940M number(3,0), S940Y number(5,0), S941 number(2,0),
      S942 number(3,0), S943 number(2,0), S944 number(2,0), S945 number(2,0), S946 number(2,0), S947 number(2,0), S948 number(3,0), S949 number(2,0), S950 number(3,0), S951 number(3,0)
    -> REC97_All (writer MDB_ADO_1)
REC97_All (writer MDB_ADO_1)
    attributes: FileCode text(7), CASEID text(12), S902 decimal(2,0), S903A decimal(2,0), S903B decimal(2,0), S903C decimal(2,0), S903D decimal(2,0), S903E decimal(2,0), S903F decimal(2,0), S903G decimal(2,0), S903H decimal(2,0), S903X decimal(2,0), S903Z decimal(2,0), S904 decimal(2,0), S905M decimal(3,0), S905Y decimal(5,0), S906 decimal(2,0), S907 decimal(2,0), S908 decimal(3,0), S909 decimal(2,0), S910 decimal(2,0), S911 decimal(2,0), S912 decimal(2,0), S913 decimal(3,0), S914 decimal(2,0), S915 decimal(3,0), S916 decimal(2,0), S917 decimal(3,0), S918 decimal(2,0), S919 decimal(3,0),
      S920 decimal(2,0), S921 decimal(2,0), S922 decimal(2,0), S923 decimal(2,0), S924 decimal(3,0), S926 decimal(2,0), S927 decimal(2,0), S928 decimal(2,0), S929 decimal(2,0), S930 decimal(3,0), S931 decimal(2,0), S932 decimal(2,0), S933 decimal(2,0), S934 decimal(2,0), S936 decimal(2,0), S937A decimal(2,0), S937B decimal(2,0), S937C decimal(2,0), S937D decimal(2,0), S937E decimal(2,0), S937F decimal(2,0), S937G decimal(2,0), S937H decimal(2,0), S937X decimal(2,0), S937Z decimal(2,0), S938 decimal(2,0), S939 decimal(2,0), S940M decimal(3,0), S940Y decimal(5,0), S941 decimal(2,0),
      S942 decimal(3,0), S943 decimal(2,0), S944 decimal(2,0), S945 decimal(2,0), S946 decimal(2,0), S947 decimal(2,0), S948 decimal(3,0), S949 decimal(2,0), S950 decimal(3,0), S951 decimal(3,0)
RECHLB.All (reader CSV_1)
    attributes: FileCode char(7), HHID char(6), SHCOL21A number(2,0), SH21 number(3,0), SH22 number(2,0), SH23 number(3,0), SH24 number(2,0), SH25 number(2,0), SH26 number(3,0), SH27 number(2,0), SH28 number(3,0)
    -> RECHLB_All (writer MDB_ADO_1)
RECHLB_All (writer MDB_ADO_1)
    attributes: FileCode text(7), HHID text(6), SHCOL21A decimal(2,0), SH21 decimal(3,0), SH22 decimal(2,0), SH23 decimal(3,0), SH24 decimal(2,0), SH25 decimal(2,0), SH26 decimal(3,0), SH27 decimal(2,0), SH28 decimal(3,0)
RECML.All (reader CSV_1)
    attributes: FileCode char(7), CASEID char(9), IDXML number(2,0), ML0 number(2,0), ML1 number(3,0), ML2 number(2,0), ML11 char(1), ML12 char(1), ML13A number(2,0), ML13B number(2,0), ML13C number(2,0), ML13D number(2,0), ML13E number(2,0), ML13F char(1), ML13G char(1), ML13H number(2,0), ML13I number(2,0), ML13J number(2,0), ML13K number(2,0), ML13L number(2,0), ML13M number(2,0), ML13N char(1), ML13O char(1), ML13P char(1), ML13X number(2,0), ML13Y number(2,0), ML13Z number(2,0), ML14A char(1), ML14B char(1), ML14Y char(1),
      ML14Z char(1), ML15A char(1), ML15B char(1), ML15C char(1), ML16A number(2,0), ML16B char(1), ML16C char(1), ML17A number(2,0), ML17B char(1), ML17C char(1), ML18A char(1), ML18B char(1), ML18C char(1), ML19A char(1), ML19B char(1), ML19C char(1), ML19D char(1), ML19E char(1), ML19F char(1), ML19X char(1), ML19Y char(1), ML19Z char(1), ML20A number(2,0), ML20B char(1), ML20C char(1), ML21A char(1), ML21B char(1), ML21C char(1), ML22A char(1), ML22B char(1),
      ML22C char(1), ML23A number(2,0), ML23B char(1), ML23C char(1), ML24C char(1)
    -> RECML_All (writer MDB_ADO_1)
RECML_All (writer MDB_ADO_1)
    attributes: FileCode text(7), CASEID text(9), IDXML decimal(2,0), ML0 decimal(2,0), ML1 decimal(3,0), ML2 decimal(2,0), ML11 text(1), ML12 text(1), ML13A decimal(2,0), ML13B decimal(2,0), ML13C decimal(2,0), ML13D decimal(2,0), ML13E decimal(2,0), ML13F text(1), ML13G text(1), ML13H decimal(2,0), ML13I decimal(2,0), ML13J decimal(2,0), ML13K decimal(2,0), ML13L decimal(2,0), ML13M decimal(2,0), ML13N text(1), ML13O text(1), ML13P text(1), ML13X decimal(2,0), ML13Y decimal(2,0), ML13Z decimal(2,0), ML14A text(1), ML14B text(1), ML14Y text(1),
      ML14Z text(1), ML15A text(1), ML15B text(1), ML15C text(1), ML16A decimal(2,0), ML16B text(1), ML16C text(1), ML17A decimal(2,0), ML17B text(1), ML17C text(1), ML18A text(1), ML18B text(1), ML18C text(1), ML19A text(1), ML19B text(1), ML19C text(1), ML19D text(1), ML19E text(1), ML19F text(1), ML19X text(1), ML19Y text(1), ML19Z text(1), ML20A decimal(2,0), ML20B text(1), ML20C text(1), ML21A text(1), ML21B text(1), ML21C text(1), ML22A text(1), ML22B text(1),
      ML22C text(1), ML23A decimal(2,0), ML23B text(1), ML23C text(1), ML24C text(1)
RECH1.All (reader CSV_1)
    attributes: FileCode char(7), HHID char(5), HVIDX number(3,0), HV101 number(3,0), HV102 number(2,0), HV103 number(2,0), HV104 number(2,0), HV105 number(3,0), HV106 number(2,0), HV107 number(2,0), HV108 number(3,0), HV109 number(2,0), HV110 char(1), HV111 char(1), HV112 char(1), HV113 char(1), HV114 char(1), HV115 char(1), HV116 number(2,0), HV117 number(2,0), HV118 number(2,0), HV120 number(2,0), HV121 number(2,0), HV122 number(2,0), HV123 number(2,0), HV124 number(3,0), HV125 char(1), HV126 char(1), HV127 char(1), HV128 char(1),
      HV129 char(1), HV140 number(2,0)
    -> RECH1_All (writer MDB_ADO_1)
RECH1_All (writer MDB_ADO_1)
    attributes: FileCode text(7), HHID text(5), HVIDX decimal(3,0), HV101 decimal(3,0), HV102 decimal(2,0), HV103 decimal(2,0), HV104 decimal(2,0), HV105 decimal(3,0), HV106 decimal(2,0), HV107 decimal(2,0), HV108 decimal(3,0), HV109 decimal(2,0), HV110 text(1), HV111 text(1), HV112 text(1), HV113 text(1), HV114 text(1), HV115 text(1), HV116 decimal(2,0), HV117 decimal(2,0), HV118 decimal(2,0), HV120 decimal(2,0), HV121 decimal(2,0), HV122 decimal(2,0), HV123 decimal(2,0), HV124 decimal(3,0), HV125 text(1), HV126 text(1), HV127 text(1), HV128 text(1),
      HV129 text(1), HV140 decimal(2,0)
REC31.All (reader CSV_1)
    attributes: FileCode char(7), CASEID char(9), V301 char(1), V302 char(1), V302A number(2,0), REC31_GROUP number(2,0), V304A char(1), V304 char(1), V305 char(1), V307 number(2,0)
    -> REC31_All (writer MDB_ADO_1)
REC31_All (writer MDB_ADO_1)
    attributes: FileCode text(7), CASEID text(9), V301 text(1), V302 text(1), V302A decimal(2,0), REC31_GROUP decimal(2,0), V304A text(1), V304 text(1), V305 text(1), V307 decimal(2,0)
RECHW.All (reader CSV_1)
    attributes: FileCode char(7), HHID char(6), SHCOLD number(2,0), SH215 number(3,0), SH216 number(6,0), SH217 number(5,0), SH240 number(4,0)
    -> RECHW_All (writer MDB_ADO_1)
RECHW_All (writer MDB_ADO_1)
    attributes: FileCode text(7), HHID text(6), SHCOLD decimal(2,0), SH215 decimal(3,0), SH216 decimal(6,0), SH217 decimal(5,0), SH240 decimal(4,0)
REC96.All (reader CSV_1)
    attributes: FileCode char(7), CASEID char(12), IDX96 number(2,0), S566 number(2,0), S567 number(3,0), S568A number(2,0), S568B number(2,0), S568C number(2,0), S568D number(2,0), S568E number(2,0), S569A number(2,0), S569B number(2,0), S569C number(2,0), S569D number(2,0), S569E number(2,0), S570A number(2,0), S570B number(2,0), S570C number(2,0), S570D number(2,0), S570X number(2,0), S571 number(2,0), S572A number(2,0), S572B number(2,0), S572C number(2,0), S572D number(2,0), S572X number(2,0), S572Y number(2,0), S573 number(3,0), S574 number(3,0)
    -> REC96_All (writer MDB_ADO_1)
REC96_All (writer MDB_ADO_1)
    attributes: FileCode text(7), CASEID text(12), IDX96 decimal(2,0), S566 decimal(2,0), S567 decimal(3,0), S568A decimal(2,0), S568B decimal(2,0), S568C decimal(2,0), S568D decimal(2,0), S568E decimal(2,0), S569A decimal(2,0), S569B decimal(2,0), S569C decimal(2,0), S569D decimal(2,0), S569E decimal(2,0), S570A decimal(2,0), S570B decimal(2,0), S570C decimal(2,0), S570D decimal(2,0), S570X decimal(2,0), S571 decimal(2,0), S572A decimal(2,0), S572B decimal(2,0), S572C decimal(2,0), S572D decimal(2,0), S572X decimal(2,0), S572Y decimal(2,0), S573 decimal(3,0), S574 decimal(3,0)
REC71.All (reader CSV_1)
    attributes: FileCode char(7), CASEID char(9), V701 number(2,0), V702 number(2,0), V704 number(3,0), V705 char(1), V714 number(2,0), V714A number(2,0), V715 number(3,0), V716 number(3,0), V717 char(1), V719 number(2,0), V721 char(1), V729 number(2,0), V730 number(3,0), V731 number(2,0), V732 number(2,0), V739 number(2,0), V740 char(1), V741 number(2,0), V743A number(2,0), V743B number(2,0), V743C char(1), V743D number(2,0), V743E char(1), V743F char(1), V744A number(2,0), V744B number(2,0), V744C number(2,0), V744D number(2,0),
      V744E number(2,0), V745A char(1), V745B char(1), V746 char(1)
    -> REC71_All (writer MDB_ADO_1)
REC71_All (writer MDB_ADO_1)
    attributes: FileCode text(7), CASEID text(9), V701 decimal(2,0), V702 decimal(2,0), V704 decimal(3,0), V705 text(1), V714 decimal(2,0), V714A decimal(2,0), V715 decimal(3,0), V716 decimal(3,0), V717 text(1), V719 decimal(2,0), V721 text(1), V729 decimal(2,0), V730 decimal(3,0), V731 decimal(2,0), V732 decimal(2,0), V739 decimal(2,0), V740 text(1), V741 decimal(2,0), V743A decimal(2,0), V743B decimal(2,0), V743C text(1), V743D decimal(2,0), V743E text(1), V743F text(1), V744A decimal(2,0), V744B decimal(2,0), V744C decimal(2,0), V744D decimal(2,0),
      V744E decimal(2,0), V745A text(1), V745B text(1), V746 text(1)
RECDV.All (reader CSV_1)
    attributes: FileCode char(7), CASEID char(9), D005 number(8,0), D101A number(2,0), D101B number(2,0), D101C number(2,0), D101D number(2,0), D101E number(2,0), D101F number(2,0), D101G number(2,0), D101H char(1), D101I char(1), D101J char(1), D102 number(2,0), D103A number(2,0), D103B number(2,0), D103C char(1), D103D char(1), D103E char(1), D103F char(1), D104 number(2,0), D105A number(2,0), D105B number(2,0), D105C number(2,0), D105D number(2,0), D105E number(2,0), D105F number(2,0), D105G number(2,0), D105H number(2,0), D105I number(2,0),
      D105J char(1), D105K char(1), D105L char(1), D105M char(1), D105N char(1), D106 number(2,0), D107 number(2,0), D108 number(2,0), D109 number(3,0), D110A number(2,0), D110B number(2,0), D110C number(2,0), D110D char(1), D110E char(1), D110F char(1), D110G char(1), D110H char(1), D111 number(2,0), D112 number(2,0), D112A number(2,0), D113 number(2,0), D114 number(2,0), D115B number(2,0), D115C number(2,0), D115D number(2,0), D115E number(2,0), D115F number(2,0), D115G number(2,0), D115H char(1), D115I char(1),
      D115J number(2,0), D115K number(2,0), D115L number(2,0), D115M number(2,0), D115N number(2,0), D115O number(2,0), D115P number(2,0), D115Q number(2,0), D115R number(2,0), D115S number(2,0), D115T number(2,0), D115U char(1), D115V number(2,0), D115W number(2,0), D115X number(2,0), D115Y number(2,0), D115XA number(2,0), D115XB char(1), D115XC char(1), D115XD char(1), D115XE char(1), D115XF char(1), D115XG char(1), D115XH char(1), D115XI char(1), D115XJ char(1), D115XK char(1), D116 number(3,0), D117A number(2,0), D118A char(1),
      D118B number(2,0), D118C number(2,0), D118D number(2,0), D118E number(2,0), D118F number(2,0), D118G number(2,0), D118H char(1), D118I char(1), D118J number(2,0), D118K number(2,0), D118L number(2,0), D118M number(2,0), D118N number(2,0), D118O number(2,0), D118P number(2,0), D118Q number(2,0), D118R number(2,0), D118S number(2,0), D118T number(2,0), D118U char(1), D118V number(2,0), D118W number(2,0), D118X number(2,0), D118Y number(2,0), D118XA number(2,0), D118XB char(1), D118XC char(1), D118XD char(1), D118XE char(1), D118XF char(1),
      D118XG char(1), D118XH char(1), D118XI char(1), D118XJ char(1), D118XK char(1), D119A char(1), D119B number(2,0), D119C number(2,0), D119D number(2,0), D119E number(2,0), D119F number(2,0), D119G number(2,0), D119H char(1), D119I char(1), D119J number(2,0), D119K number(2,0), D119L number(2,0), D119M number(2,0), D119N number(2,0), D119O number(2,0), D119P number(2,0), D119Q number(2,0), D119R number(2,0), D119S number(2,0), D119T number(2,0), D119U char(1), D119V number(2,0), D119W number(2,0), D119X number(2,0), D119Y number(2,0),
      D119XA number(2,0), D119XB char(1), D119XC char(1), D119XD char(1), D119XE char(1), D119XF char(1), D119XG char(1), D119XH char(1), D119XI char(1), D119XJ char(1), D119XK char(1), D120 number(3,0), D121 number(2,0), D122A number(2,0), D122B number(2,0), D122C number(2,0), D123 char(1), D124 char(1), D125 char(1), D126 char(1), D127 char(1), D128 char(1), D129 char(1), D130A char(1), D130B char(1), D100A number(2,0), D100B number(2,0), D100C number(2,0), D100D number(2,0), D112N char(1),
      D117 char(1), D121A number(2,0), D1310A number(2,0), D1310B number(3,0)
    -> RECDV_All (writer MDB_ADO_1)
RECDV_All (writer MDB_ADO_1)
    attributes: FileCode text(7), CASEID text(9), D005 decimal(8,0), D101A decimal(2,0), D101B decimal(2,0), D101C decimal(2,0), D101D decimal(2,0), D101E decimal(2,0), D101F decimal(2,0), D101G decimal(2,0), D101H text(1), D101I text(1), D101J text(1), D102 decimal(2,0), D103A decimal(2,0), D103B decimal(2,0), D103C text(1), D103D text(1), D103E text(1), D103F text(1), D104 decimal(2,0), D105A decimal(2,0), D105B decimal(2,0), D105C decimal(2,0), D105D decimal(2,0), D105E decimal(2,0), D105F decimal(2,0), D105G decimal(2,0), D105H decimal(2,0), D105I decimal(2,0),
      D105J text(1), D105K text(1), D105L text(1), D105M text(1), D105N text(1), D106 decimal(2,0), D107 decimal(2,0), D108 decimal(2,0), D109 decimal(3,0), D110A decimal(2,0), D110B decimal(2,0), D110C decimal(2,0), D110D text(1), D110E text(1), D110F text(1), D110G text(1), D110H text(1), D111 decimal(2,0), D112 decimal(2,0), D112A decimal(2,0), D113 decimal(2,0), D114 decimal(2,0), D115B decimal(2,0), D115C decimal(2,0), D115D decimal(2,0), D115E decimal(2,0), D115F decimal(2,0), D115G decimal(2,0), D115H text(1), D115I text(1),
      D115J decimal(2,0), D115K decimal(2,0), D115L decimal(2,0), D115M decimal(2,0), D115N decimal(2,0), D115O decimal(2,0), D115P decimal(2,0), D115Q decimal(2,0), D115R decimal(2,0), D115S decimal(2,0), D115T decimal(2,0), D115U text(1), D115V decimal(2,0), D115W decimal(2,0), D115X decimal(2,0), D115Y decimal(2,0), D115XA decimal(2,0), D115XB text(1), D115XC text(1), D115XD text(1), D115XE text(1), D115XF text(1), D115XG text(1), D115XH text(1), D115XI text(1), D115XJ text(1), D115XK text(1), D116 decimal(3,0), D117A decimal(2,0), D118A text(1),
      D118B decimal(2,0), D118C decimal(2,0), D118D decimal(2,0), D118E decimal(2,0), D118F decimal(2,0), D118G decimal(2,0), D118H text(1), D118I text(1), D118J decimal(2,0), D118K decimal(2,0), D118L decimal(2,0), D118M decimal(2,0), D118N decimal(2,0), D118O decimal(2,0), D118P decimal(2,0), D118Q decimal(2,0), D118R decimal(2,0), D118S decimal(2,0), D118T decimal(2,0), D118U text(1), D118V decimal(2,0), D118W decimal(2,0), D118X decimal(2,0), D118Y decimal(2,0), D118XA decimal(2,0), D118XB text(1), D118XC text(1), D118XD text(1), D118XE text(1), D118XF text(1),
      D118XG text(1), D118XH text(1), D118XI text(1), D118XJ text(1), D118XK text(1), D119A text(1), D119B decimal(2,0), D119C decimal(2,0), D119D decimal(2,0), D119E decimal(2,0), D119F decimal(2,0), D119G decimal(2,0), D119H text(1), D119I text(1), D119J decimal(2,0), D119K decimal(2,0), D119L decimal(2,0), D119M decimal(2,0), D119N decimal(2,0), D119O decimal(2,0), D119P decimal(2,0), D119Q decimal(2,0), D119R decimal(2,0), D119S decimal(2,0), D119T decimal(2,0), D119U text(1), D119V decimal(2,0), D119W decimal(2,0), D119X decimal(2,0), D119Y decimal(2,0),
      D119XA decimal(2,0), D119XB text(1), D119XC text(1), D119XD text(1), D119XE text(1), D119XF text(1), D119XG text(1), D119XH text(1), D119XI text(1), D119XJ text(1), D119XK text(1), D120 decimal(3,0), D121 decimal(2,0), D122A decimal(2,0), D122B decimal(2,0), D122C decimal(2,0), D123 text(1), D124 text(1), D125 text(1), D126 text(1), D127 text(1), D128 text(1), D129 text(1), D130A text(1), D130B text(1), D100A decimal(2,0), D100B decimal(2,0), D100C decimal(2,0), D100D decimal(2,0), D112N text(1),
      D117 text(1), D121A decimal(2,0), D1310A decimal(2,0), D1310B decimal(3,0)
RECHMH.All (reader CSV_1)
    attributes: FileCode char(7), HHID char(6), HMHIDX number(3,0), HML12 number(2,0), HML13 number(2,0), HML14 number(2,0), HML15 char(1), HML16 number(3,0), HML16A number(3,0), HML17 number(2,0), HML18 number(2,0), HML19 number(2,0), HML20 number(2,0), HML30 number(2,0), HML31 number(2,0), HML32 number(2,0), HML32A char(1), HML32B char(1), HML32C char(1), HML32D char(1), HML32E char(1), HML32F char(1), HML32G char(1), HML33 char(1), HML34 char(6), HML35 number(2,0)
    -> RECHMH_All (writer MDB_ADO_1)
RECHMH_All (writer MDB_ADO_1)
    attributes: FileCode text(7), HHID text(6), HMHIDX decimal(3,0), HML12 decimal(2,0), HML13 decimal(2,0), HML14 decimal(2,0), HML15 text(1), HML16 decimal(3,0), HML16A decimal(3,0), HML17 decimal(2,0), HML18 decimal(2,0), HML19 decimal(2,0), HML20 decimal(2,0), HML30 decimal(2,0), HML31 decimal(2,0), HML32 decimal(2,0), HML32A text(1), HML32B text(1), HML32C text(1), HML32D text(1), HML32E text(1), HML32F text(1), HML32G text(1), HML33 text(1), HML34 text(6), HML35 decimal(2,0)
RECH0.All (reader CSV_1)
    attributes: FileCode char(7), HHID char(6), HV000 char(4), HV001 number(3,0), HV002 number(4,0), HV003 number(2,0), HV004 number(3,0), HV005 number(7,0), HV006 number(3,0), HV007 number(5,0), HV008 number(5,0), HV009 number(3,0), HV010 number(2,0), HV011 number(2,0), HV012 number(3,0), HV013 number(3,0), HV014 number(2,0), HV015 number(2,0), HV016 number(3,0), HV017 number(2,0), HV018 number(4,0), HV019 number(2,0), HV020 number(2,0), HV021 number(3,0), HV022 number(3,0), HV023 number(3,0), HV024 number(2,0), HV025 number(2,0), HV026 number(2,0), HV027 number(2,0),
      HV028 number(7,0), HV030 number(3,0), HV031 number(3,0), HV032 number(2,0), HV035 number(2,0), HV040 number(3,0), HV041 number(2,0), HV042 number(2,0), HV044 char(1)
    -> RECH0_All (writer MDB_ADO_1)
RECH0_All (writer MDB_ADO_1)
    attributes: FileCode text(7), HHID text(6), HV000 text(4), HV001 decimal(3,0), HV002 decimal(4,0), HV003 decimal(2,0), HV004 decimal(3,0), HV005 decimal(7,0), HV006 decimal(3,0), HV007 decimal(5,0), HV008 decimal(5,0), HV009 decimal(3,0), HV010 decimal(2,0), HV011 decimal(2,0), HV012 decimal(3,0), HV013 decimal(3,0), HV014 decimal(2,0), HV015 decimal(2,0), HV016 decimal(3,0), HV017 decimal(2,0), HV018 decimal(4,0), HV019 decimal(2,0), HV020 decimal(2,0), HV021 decimal(3,0), HV022 decimal(3,0), HV023 decimal(3,0), HV024 decimal(2,0), HV025 decimal(2,0), HV026 decimal(2,0), HV027 decimal(2,0),
      HV028 decimal(7,0), HV030 decimal(3,0), HV031 decimal(3,0), HV032 decimal(2,0), HV035 decimal(2,0), HV040 decimal(3,0), HV041 decimal(2,0), HV042 decimal(2,0), HV044 text(1)
RECHC.All (reader CSV_1)
    attributes: FileCode char(7), HHID char(7), SHCOLC number(2,0), SH202 number(3,0), SH205 number(5,0), SH206 number(5,0), SH212 number(4,0)
    -> RECHC_All (writer MDB_ADO_1)
RECHC_All (writer MDB_ADO_1)
    attributes: FileCode text(7), HHID text(7), SHCOLC decimal(2,0), SH202 decimal(3,0), SH205 decimal(5,0), SH206 decimal(5,0), SH212 decimal(4,0)
RECG2.All (reader CSV_1)
    attributes: FileCode char(7), CASEID char(9), GIDX number(2,0), G121 number(2,0), G122 number(3,0), G123 number(2,0), G124 number(3,0)
    -> RECG2_All (writer MDB_ADO_1)
RECG2_All (writer MDB_ADO_1)
    attributes: FileCode text(7), CASEID text(9), GIDX decimal(2,0), G121 decimal(2,0), G122 decimal(3,0), G123 decimal(2,0), G124 decimal(3,0)
REC22.All (reader CSV_1)
    attributes: FileCode char(7), CASEID char(9), V201 number(3,0), V202 number(2,0), V203 number(2,0), V204 number(2,0), V205 number(2,0), V206 number(2,0), V207 number(2,0), V208 number(2,0), V209 number(2,0), V210 number(2,0), V211 number(5,0), V212 number(3,0), V213 number(2,0), V214 number(2,0), V215 number(4,0), V216 number(2,0), V217 char(1), V218 number(2,0), V219 number(2,0), V220 number(2,0), V221 number(4,0), V222 number(4,0), V223 number(2,0), V224 number(3,0), V225 number(2,0), V226 number(4,0), V227 number(2,0), V228 number(2,0),
      V229 number(3,0), V230 number(5,0), V231 number(5,0), V232 number(2,0), V233 number(2,0), V234 number(2,0), V235 number(2,0), V237 number(2,0), V238 number(2,0), V239 number(2,0), V240 number(3,0), V241 number(5,0), V242 number(5,0), V243 number(2,0)
    -> REC22_All (writer MDB_ADO_1)
REC22_All (writer MDB_ADO_1)
    attributes: FileCode text(7), CASEID text(9), V201 decimal(3,0), V202 decimal(2,0), V203 decimal(2,0), V204 decimal(2,0), V205 decimal(2,0), V206 decimal(2,0), V207 decimal(2,0), V208 decimal(2,0), V209 decimal(2,0), V210 decimal(2,0), V211 decimal(5,0), V212 decimal(3,0), V213 decimal(2,0), V214 decimal(2,0), V215 decimal(4,0), V216 decimal(2,0), V217 text(1), V218 decimal(2,0), V219 decimal(2,0), V220 decimal(2,0), V221 decimal(4,0), V222 decimal(4,0), V223 decimal(2,0), V224 decimal(3,0), V225 decimal(2,0), V226 decimal(4,0), V227 decimal(2,0), V228 decimal(2,0),
      V229 decimal(3,0), V230 decimal(5,0), V231 decimal(5,0), V232 decimal(2,0), V233 decimal(2,0), V234 decimal(2,0), V235 decimal(2,0), V237 decimal(2,0), V238 decimal(2,0), V239 decimal(2,0), V240 decimal(3,0), V241 decimal(5,0), V242 decimal(5,0), V243 decimal(2,0)
RECHOV.All (reader CSV_1)
    attributes: FileCode char(7), HHID char(7), HOVIDX number(3,0), HO100 number(3,0), HO101 number(2,0), HO102 number(2,0), HO103 number(2,0), HO104 number(2,0), HO105 number(2,0), HO106 number(2,0), HO107 number(2,0), HO108 number(2,0)
    -> RECHOV_All (writer MDB_ADO_1)
RECHOV_All (writer MDB_ADO_1)
    attributes: FileCode text(7), HHID text(7), HOVIDX decimal(3,0), HO100 decimal(3,0), HO101 decimal(2,0), HO102 decimal(2,0), HO103 decimal(2,0), HO104 decimal(2,0), HO105 decimal(2,0), HO106 decimal(2,0), HO107 decimal(2,0), HO108 decimal(2,0)
REC95.All (reader CSV_1)
    attributes: FileCode char(7), CASEID char(9), IDX95 number(2,0), S506AD number(3,0), S506AM number(3,0), S506AY number(5,0), SHB1 number(2,0), SHB1D number(3,0), SHB1M number(3,0), SHB1Y number(5,0), SHB2 number(2,0), SHB2D number(3,0), SHB2M number(3,0), SHB2Y number(5,0), SHB3 number(2,0), SHB3D number(3,0), SHB3M number(3,0), SHB3Y number(5,0), S510J number(2,0), S519J number(2,0), S522C number(2,0), S522D number(2,0), S523A number(2,0), S523B number(2,0), S523C number(2,0), S523D number(2,0), S523E number(2,0), S523F number(2,0), S523G number(2,0), S523H number(2,0),
      S523I number(2,0), S523J number(2,0), S523K number(2,0), S523L number(2,0), S523M number(2,0), S523N number(2,0), S523O number(2,0), S523P number(2,0), S523Q number(2,0), S523R number(2,0), S523S number(2,0), S523T number(2,0), S523U number(2,0), S523V number(2,0), S523W number(2,0), S523X number(2,0), S536A number(2,0), S536K number(2,0), S536B number(3,0), S536C number(3,0), S536D char(1), S538O number(2,0), S538P number(2,0), S539 number(2,0), S540A number(2,0), S540B number(2,0), S540C number(2,0), S540D number(2,0), S540E number(2,0), S540F number(2,0),
      S540G number(2,0), S540H number(2,0), S540I number(2,0), S540J number(2,0), S540K number(2,0), S540L number(2,0), S540W number(2,0), S540X number(2,0), S541A number(2,0), S541B number(2,0), S541C number(2,0), S541D number(2,0), S541E number(2,0), S541F number(2,0), S541G number(2,0), S541H number(2,0), S541I number(2,0), S541J number(2,0), S541K number(2,0), S541L number(2,0), S541M number(2,0), S541N number(2,0), S541O number(2,0), S541P number(2,0), S541Q number(2,0), S541R number(2,0), S541S number(2,0), S541T number(2,0), S541U number(2,0), S541V number(2,0),
      S541W number(2,0), S541X number(2,0), S541Y number(2,0)
    -> REC95_All (writer MDB_ADO_1)
REC95_All (writer MDB_ADO_1)
    attributes: FileCode text(7), CASEID text(9), IDX95 decimal(2,0), S506AD decimal(3,0), S506AM decimal(3,0), S506AY decimal(5,0), SHB1 decimal(2,0), SHB1D decimal(3,0), SHB1M decimal(3,0), SHB1Y decimal(5,0), SHB2 decimal(2,0), SHB2D decimal(3,0), SHB2M decimal(3,0), SHB2Y decimal(5,0), SHB3 decimal(2,0), SHB3D decimal(3,0), SHB3M decimal(3,0), SHB3Y decimal(5,0), S510J decimal(2,0), S519J decimal(2,0), S522C decimal(2,0), S522D decimal(2,0), S523A decimal(2,0), S523B decimal(2,0), S523C decimal(2,0), S523D decimal(2,0), S523E decimal(2,0), S523F decimal(2,0), S523G decimal(2,0), S523H decimal(2,0),
      S523I decimal(2,0), S523J decimal(2,0), S523K decimal(2,0), S523L decimal(2,0), S523M decimal(2,0), S523N decimal(2,0), S523O decimal(2,0), S523P decimal(2,0), S523Q decimal(2,0), S523R decimal(2,0), S523S decimal(2,0), S523T decimal(2,0), S523U decimal(2,0), S523V decimal(2,0), S523W decimal(2,0), S523X decimal(2,0), S536A decimal(2,0), S536K decimal(2,0), S536B decimal(3,0), S536C decimal(3,0), S536D text(1), S538O decimal(2,0), S538P decimal(2,0), S539 decimal(2,0), S540A decimal(2,0), S540B decimal(2,0), S540C decimal(2,0), S540D decimal(2,0), S540E decimal(2,0), S540F decimal(2,0),
      S540G decimal(2,0), S540H decimal(2,0), S540I decimal(2,0), S540J decimal(2,0), S540K decimal(2,0), S540L decimal(2,0), S540W decimal(2,0), S540X decimal(2,0), S541A decimal(2,0), S541B decimal(2,0), S541C decimal(2,0), S541D decimal(2,0), S541E decimal(2,0), S541F decimal(2,0), S541G decimal(2,0), S541H decimal(2,0), S541I decimal(2,0), S541J decimal(2,0), S541K decimal(2,0), S541L decimal(2,0), S541M decimal(2,0), S541N decimal(2,0), S541O decimal(2,0), S541P decimal(2,0), S541Q decimal(2,0), S541R decimal(2,0), S541S decimal(2,0), S541T decimal(2,0), S541U decimal(2,0), S541V decimal(2,0),
      S541W decimal(2,0), S541X decimal(2,0), S541Y decimal(2,0)
RECH9.All (reader CSV_1)
    attributes: FileCode char(7), HHID number(9,0), SHIDX9 number(2,0), SH78O number(3,0), SH79 number(3,0), SH80 number(4,0), SH81 number(3,0), SH82 number(2,0), SH83 number(2,0)
    -> RECH9_All (writer MDB_ADO_1)
RECH9_All (writer MDB_ADO_1)
    attributes: FileCode text(7), HHID decimal(9,0), SHIDX9 decimal(2,0), SH78O decimal(3,0), SH79 decimal(3,0), SH80 decimal(4,0), SH81 decimal(3,0), SH82 decimal(2,0), SH83 decimal(2,0)
RECG1.All (reader CSV_1)
    attributes: FileCode char(7), CASEID char(9), G100 number(2,0), G101 number(2,0), G102 number(2,0), G103 number(2,0), G104 number(2,0), G105 number(2,0), G106 number(3,0), G107 number(3,0), G108 number(3,0), G109 char(1), G110 char(1), G111 char(1), G112 char(1), G113 char(1), G114 char(1), G115 char(1), G116 char(1), G117A char(1), G117B char(1), G117C char(1), G117D char(1), G117E char(1), G117F char(1), G117G char(1), G117H char(1), G117I char(1), G117J char(1), G117X char(1),
      G117Y char(1), G118 number(2,0), G119 number(2,0)
    -> RECG1_All (writer MDB_ADO_1)
RECG1_All (writer MDB_ADO_1)
    attributes: FileCode text(7), CASEID text(9), G100 decimal(2,0), G101 decimal(2,0), G102 decimal(2,0), G103 decimal(2,0), G104 decimal(2,0), G105 decimal(2,0), G106 decimal(3,0), G107 decimal(3,0), G108 decimal(3,0), G109 text(1), G110 text(1), G111 text(1), G112 text(1), G113 text(1), G114 text(1), G115 text(1), G116 text(1), G117A text(1), G117B text(1), G117C text(1), G117D text(1), G117E text(1), G117F text(1), G117G text(1), G117H text(1), G117I text(1), G117J text(1), G117X text(1),
      G117Y text(1), G118 decimal(2,0), G119 decimal(2,0)
REC21.All (reader CSV_1)
    attributes: FileCode char(7), CASEID char(9), BIDX number(2,0), BORD number(2,0), B0 number(2,0), B1 number(3,0), B2 number(5,0), B3 number(5,0), B4 number(2,0), B5 number(2,0), B6 number(4,0), B7 number(4,0), B8 number(3,0), B9 number(2,0), B10 number(2,0), B11 number(4,0), B12 number(4,0), B13 number(2,0), B15 number(2,0), B16 number(3,0)
    -> REC21_All (writer MDB_ADO_1)
REC21_All (writer MDB_ADO_1)
    attributes: FileCode text(7), CASEID text(9), BIDX decimal(2,0), BORD decimal(2,0), B0 decimal(2,0), B1 decimal(3,0), B2 decimal(5,0), B3 decimal(5,0), B4 decimal(2,0), B5 decimal(2,0), B6 decimal(4,0), B7 decimal(4,0), B8 decimal(3,0), B9 decimal(2,0), B10 decimal(2,0), B11 decimal(4,0), B12 decimal(4,0), B13 decimal(2,0), B15 decimal(2,0), B16 decimal(3,0)
REC94.All (reader CSV_1)
    attributes: FileCode char(7), CASEID char(9), IDX94 number(2,0), S410J number(2,0), S433L number(2,0), S435C number(2,0), S435D number(2,0), S435E number(2,0), S435F number(2,0), S435GA number(2,0), S435GB number(2,0), S435GC number(2,0), S435GD number(2,0), S435GE number(2,0), S435GF number(2,0), S435GG number(2,0), S435GH number(2,0), S435GI number(2,0), S435GJ number(2,0), S435GK number(2,0), S435GL number(2,0), S435GM number(2,0), S435GN number(2,0), S435GX number(2,0), S435GZ number(2,0), S435H number(4,0), S435I number(2,0), S435J number(2,0), S439A number(3,0)
    -> REC94_All (writer MDB_ADO_1)
REC94_All (writer MDB_ADO_1)
    attributes: FileCode text(7), CASEID text(9), IDX94 decimal(2,0), S410J decimal(2,0), S433L decimal(2,0), S435C decimal(2,0), S435D decimal(2,0), S435E decimal(2,0), S435F decimal(2,0), S435GA decimal(2,0), S435GB decimal(2,0), S435GC decimal(2,0), S435GD decimal(2,0), S435GE decimal(2,0), S435GF decimal(2,0), S435GG decimal(2,0), S435GH decimal(2,0), S435GI decimal(2,0), S435GJ decimal(2,0), S435GK decimal(2,0), S435GL decimal(2,0), S435GM decimal(2,0), S435GN decimal(2,0), S435GX decimal(2,0), S435GZ decimal(2,0), S435H decimal(4,0), S435I decimal(2,0), S435J decimal(2,0), S439A decimal(3,0)
RECH8.All (reader CSV_1)
    attributes: FileCode char(7), HHID char(5), SHCOL3B number(2,0), SH223 number(3,0), SH225 number(3,0), SH226 number(3,0), SH227 number(6,0), SH227AA number(6,0), SH227AB number(6,0), SH227AC number(6,0), SH227AD number(6,0), SH227AE number(6,0), SH227AF number(6,0), SH227AG number(6,0), SH228 number(2,0), SH229 number(3,0), SH230 number(3,0), SH231 number(6,0), SH231AA number(6,0), SH231AB number(6,0), SH231AC number(6,0), SH231AD number(6,0), SH231AE number(6,0), SH231AF number(6,0), SH231AG number(6,0), SH232 number(2,0), SH233 number(3,0), SH234 number(2,0), SH235 number(6,0), SH235AA number(6,0),
      SH235AB number(6,0), SH235AC number(6,0), SH235AD number(6,0), SH235AE number(6,0), SH235AF number(6,0), SH235AG number(6,0), SH236 number(2,0), SH237 char(1), SH238 char(1), SH239 number(2,0), SH240 number(2,0)
    -> RECH8_All (writer MDB_ADO_1)
RECH8_All (writer MDB_ADO_1)
    attributes: FileCode text(7), HHID text(5), SHCOL3B decimal(2,0), SH223 decimal(3,0), SH225 decimal(3,0), SH226 decimal(3,0), SH227 decimal(6,0), SH227AA decimal(6,0), SH227AB decimal(6,0), SH227AC decimal(6,0), SH227AD decimal(6,0), SH227AE decimal(6,0), SH227AF decimal(6,0), SH227AG decimal(6,0), SH228 decimal(2,0), SH229 decimal(3,0), SH230 decimal(3,0), SH231 decimal(6,0), SH231AA decimal(6,0), SH231AB decimal(6,0), SH231AC decimal(6,0), SH231AD decimal(6,0), SH231AE decimal(6,0), SH231AF decimal(6,0), SH231AG decimal(6,0), SH232 decimal(2,0), SH233 decimal(3,0), SH234 decimal(2,0), SH235 decimal(6,0), SH235AA decimal(6,0),
      SH235AB decimal(6,0), SH235AC decimal(6,0), SH235AD decimal(6,0), SH235AE decimal(6,0), SH235AF decimal(6,0), SH235AG decimal(6,0), SH236 decimal(2,0), SH237 text(1), SH238 text(1), SH239 decimal(2,0), SH240 decimal(2,0)
REC61.All (reader CSV_1)
    attributes: FileCode char(7), CASEID char(9), V602 number(2,0), V603 number(4,0), V604 number(2,0), V605 number(2,0), V613 number(3,0), V614 number(2,0), V616 number(4,0), V621 number(2,0), V623 number(2,0), V624 number(2,0), V625 number(2,0), V626 number(2,0), V625A number(2,0), V626A number(2,0), V627 number(3,0), V628 number(3,0), V629 number(3,0), V631 char(1), V632 number(2,0), V633A char(1), V633B char(1), V633C char(1), V633D char(1), V633E char(1), V633F char(1), V633G char(1), V634 char(1)
    -> REC61_All (writer MDB_ADO_1)
REC61_All (writer MDB_ADO_1)
    attributes: FileCode text(7), CASEID text(9), V602 decimal(2,0), V603 decimal(4,0), V604 decimal(2,0), V605 decimal(2,0), V613 decimal(3,0), V614 decimal(2,0), V616 decimal(4,0), V621 decimal(2,0), V623 decimal(2,0), V624 decimal(2,0), V625 decimal(2,0), V626 decimal(2,0), V625A decimal(2,0), V626A decimal(2,0), V627 decimal(3,0), V628 decimal(3,0), V629 decimal(3,0), V631 text(1), V632 decimal(2,0), V633A text(1), V633B text(1), V633C text(1), V633D text(1), V633E text(1), V633F text(1), V633G text(1), V634 text(1)
RECHA.All (reader CSV_1)
    attributes: FileCode char(7), HHID char(7), SHCOLA number(2,0), SH53 number(3,0), SH54 number(2,0), SH55 number(2,0), SH56 number(2,0), SH57 number(2,0)
    -> RECHA_All (writer MDB_ADO_1)
RECHA_All (writer MDB_ADO_1)
    attributes: FileCode text(7), HHID text(7), SHCOLA decimal(2,0), SH53 decimal(3,0), SH54 decimal(2,0), SH55 decimal(2,0), SH56 decimal(2,0), SH57 decimal(2,0)
RECHSK.All (reader CSV_1)
    attributes: FileCode char(7), HHID char(7), HSKIDX number(3,0), HS100 number(2,0), HS101 number(2,0), HS102 number(2,0), HS103 number(2,0), HS104 number(2,0), HS105 number(2,0), HS106 number(2,0), HS107 number(2,0), HS108 number(2,0), HS109 number(2,0), HS110 number(2,0), HS111 number(2,0)
    -> RECHSK_All (writer MDB_ADO_1)
RECHSK_All (writer MDB_ADO_1)
    attributes: FileCode text(7), HHID text(7), HSKIDX decimal(3,0), HS100 decimal(2,0), HS101 decimal(2,0), HS102 decimal(2,0), HS103 decimal(2,0), HS104 decimal(2,0), HS105 decimal(2,0), HS106 decimal(2,0), HS107 decimal(2,0), HS108 decimal(2,0), HS109 decimal(2,0), HS110 decimal(2,0), HS111 decimal(2,0)
RECH7.All (reader CSV_1)
    attributes: FileCode char(7), HHID char(6), SH230 number(3,0), SH231 number(2,0), SH232 number(2,0), SH234 number(3,0), SH234C number(3,0), SH235 number(2,0), SH237 number(2,0), SH238 number(2,0), SH239 number(3,0), SH241 number(2,0), SH242A number(2,0), SH242B number(2,0), SH242C number(2,0), SH243 number(3,0), SH244 number(2,0), SH245 number(5,0), SH246S number(4,0), SH246D number(4,0), SH248 number(2,0), SH249 number(2,0), SH250 number(2,0), SH253 number(5,0), SH254 number(2,0), SH255S number(4,0), SH255D number(4,0), SH257 number(2,0), SH258 number(2,0), SH259 number(2,0),
      SH260 number(2,0), SH262 number(5,0), SH263 number(2,0), SH264S number(4,0), SH264D number(4,0), FSYSTO number(4,0), FDYSTO number(4,0), SH271 number(5,0), SH273 number(5,0), SH276 number(2,0), SHWH number(2,0), SH1 number(14,0), SH1D number(3,0), SH1MO number(3,0), SH1Y number(5,0), SH1H number(3,0), SH1M number(3,0), SH1X number(2,0), SH2 number(14,0), SH2D number(3,0), SH2MO number(3,0), SH2Y number(5,0), SH2H number(3,0), SH2M number(3,0), SH2X number(2,0), SH3 number(14,0), SH3D number(3,0), SH3MO number(3,0), SH3Y number(5,0), SH3H number(3,0),
      SH3M number(3,0), SH3X number(2,0), SH279 number(2,0), SH280 number(5,0), SH281 number(5,0), SH283 number(9,0), SH283D number(3,0), SH283M number(3,0), SH283Y number(5,0), SH283T number(5,0), SH284 number(4,0), SH284A number(4,0), SH284G number(4,0), SH284B number(4,0), SHPC1 number(5,0), SHSD1 number(5,0), SHRM1 number(6,0), SHRM3 number(6,0), SHRM4 number(6,0), SHRM5 number(6,0), SHSD3 number(5,0), SHBM number(5,0), SHRI number(5,0), SHCMC number(4,0), SHFLG number(2,0), SHSMK char(1), SHRESI number(2,0), SHED1 number(2,0), SHED2 number(3,0), SHED3 number(2,0)
    -> RECH7_All (writer MDB_ADO_1)
RECH7_All (writer MDB_ADO_1)
    attributes: FileCode text(7), HHID text(6), SH230 decimal(3,0), SH231 decimal(2,0), SH232 decimal(2,0), SH234 decimal(3,0), SH234C decimal(3,0), SH235 decimal(2,0), SH237 decimal(2,0), SH238 decimal(2,0), SH239 decimal(3,0), SH241 decimal(2,0), SH242A decimal(2,0), SH242B decimal(2,0), SH242C decimal(2,0), SH243 decimal(3,0), SH244 decimal(2,0), SH245 decimal(5,0), SH246S decimal(4,0), SH246D decimal(4,0), SH248 decimal(2,0), SH249 decimal(2,0), SH250 decimal(2,0), SH253 decimal(5,0), SH254 decimal(2,0), SH255S decimal(4,0), SH255D decimal(4,0), SH257 decimal(2,0), SH258 decimal(2,0), SH259 decimal(2,0),
      SH260 decimal(2,0), SH262 decimal(5,0), SH263 decimal(2,0), SH264S decimal(4,0), SH264D decimal(4,0), FSYSTO decimal(4,0), FDYSTO decimal(4,0), SH271 decimal(5,0), SH273 decimal(5,0), SH276 decimal(2,0), SHWH decimal(2,0), SH1 decimal(14,0), SH1D decimal(3,0), SH1MO decimal(3,0), SH1Y decimal(5,0), SH1H decimal(3,0), SH1M decimal(3,0), SH1X decimal(2,0), SH2 decimal(14,0), SH2D decimal(3,0), SH2MO decimal(3,0), SH2Y decimal(5,0), SH2H decimal(3,0), SH2M decimal(3,0), SH2X decimal(2,0), SH3 decimal(14,0), SH3D decimal(3,0), SH3MO decimal(3,0), SH3Y decimal(5,0), SH3H decimal(3,0),
      SH3M decimal(3,0), SH3X decimal(2,0), SH279 decimal(2,0), SH280 decimal(5,0), SH281 decimal(5,0), SH283 decimal(9,0), SH283D decimal(3,0), SH283M decimal(3,0), SH283Y decimal(5,0), SH283T decimal(5,0), SH284 decimal(4,0), SH284A decimal(4,0), SH284G decimal(4,0), SH284B decimal(4,0), SHPC1 decimal(5,0), SHSD1 decimal(5,0), SHRM1 decimal(6,0), SHRM3 decimal(6,0), SHRM4 decimal(6,0), SHRM5 decimal(6,0), SHSD3 decimal(5,0), SHBM decimal(5,0), SHRI decimal(5,0), SHCMC decimal(4,0), SHFLG decimal(2,0), SHSMK text(1), SHRESI decimal(2,0), SHED1 decimal(2,0), SHED2 decimal(3,0), SHED3 decimal(2,0)
RECHDP.All (reader CSV_1)
    attributes: FileCode char(7), HHID char(6), HDPIDX number(2,0), HD100 number(2,0), HD101 number(4,0)
    -> RECHDP_All (writer MDB_ADO_1)
RECHDP_All (writer MDB_ADO_1)
    attributes: FileCode text(7), HHID text(6), HDPIDX decimal(2,0), HD100 decimal(2,0), HD101 decimal(4,0)
RECHS.All (reader CSV_1)
    attributes: FileCode char(7), HHID char(6), SH67 number(3,0), SH68 number(2,0), SH69 number(2,0), SH70 number(3,0), SH71U number(2,0), SH71N number(7,0), SH72U number(2,0), SH72N number(7,0), SH73 number(2,0), SH74 number(3,0), SH75U number(2,0), SH75N number(7,0), SH76U number(2,0), SH76N number(7,0), SH77 number(2,0), SH78 number(3,0), SH79U number(2,0), SH79N number(7,0), SH80U number(2,0), SH80N number(7,0)
    -> RECHS_All (writer MDB_ADO_1)
RECHS_All (writer MDB_ADO_1)
    attributes: FileCode text(7), HHID text(6), SH67 decimal(3,0), SH68 decimal(2,0), SH69 decimal(2,0), SH70 decimal(3,0), SH71U decimal(2,0), SH71N decimal(7,0), SH72U decimal(2,0), SH72N decimal(7,0), SH73 decimal(2,0), SH74 decimal(3,0), SH75U decimal(2,0), SH75N decimal(7,0), SH76U decimal(2,0), SH76N decimal(7,0), SH77 decimal(2,0), SH78 decimal(3,0), SH79U decimal(2,0), SH79N decimal(7,0), SH80U decimal(2,0), SH80N decimal(7,0)
REC44.All (reader CSV_1)
    attributes: FileCode char(7), CASEID char(9), HWIDX number(2,0), HW1 number(3,0), HW2 number(5,0), HW3 number(5,0), HW4 number(5,0), HW5 number(5,0), HW6 number(6,0), HW7 number(5,0), HW8 number(5,0), HW9 number(6,0), HW10 number(5,0), HW11 number(5,0), HW12 number(6,0), HW13 number(2,0), HW15 number(2,0), HW16 number(3,0), HW17 number(3,0), HW18 number(3,0), HW19 number(5,0), HW51 number(3,0), HW52 number(2,0), HW53 number(4,0), HW55 number(2,0), HW56 number(5,0), HW57 number(2,0), HW58 char(1), HW70 number(5,0), HW71 number(5,0),
      HW72 number(5,0), HW73 number(5,0)
    -> REC44_All (writer MDB_ADO_1)
REC44_All (writer MDB_ADO_1)
    attributes: FileCode text(7), CASEID text(9), HWIDX decimal(2,0), HW1 decimal(3,0), HW2 decimal(5,0), HW3 decimal(5,0), HW4 decimal(5,0), HW5 decimal(5,0), HW6 decimal(6,0), HW7 decimal(5,0), HW8 decimal(5,0), HW9 decimal(6,0), HW10 decimal(5,0), HW11 decimal(5,0), HW12 decimal(6,0), HW13 decimal(2,0), HW15 decimal(2,0), HW16 decimal(3,0), HW17 decimal(3,0), HW18 decimal(3,0), HW19 decimal(5,0), HW51 decimal(3,0), HW52 decimal(2,0), HW53 decimal(4,0), HW55 decimal(2,0), HW56 decimal(5,0), HW57 decimal(2,0), HW58 text(1), HW70 decimal(5,0), HW71 decimal(5,0),
      HW72 decimal(5,0), HW73 decimal(5,0)
