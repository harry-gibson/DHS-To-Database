FME workspace check_survey_updates.fmw

Parameters:
- SourceDataset_CSV2 = $(FME_MF_DIR)missing_and_unavailable.csv   # Source CSV (Comma Separated Value) File(s)
- DestDataset_XLSXW = \\map-fs1.ndph.ox.ac.uk\map_data\DHS_Automation\Acquisition\Update_Staging\Potential_New_Surveys.xlsx   # Destination Microsoft Excel File
- FindUpdatedSince = 20150101   # "{}" Check for surveys which are already held but have been updated since when?

Readers:
- CSV2_1: CSV2 from $(SourceDataset_CSV2)

Writers:
- XLSXW_1: XLSXW to $(DestDataset_XLSXW)

Note: Main API listing, to reattach info
Junction_2
    -> FeatureMerger_4 [SUPPLIER]
API_Says_Updated_Check: Inspector
Note: missing_and_unavailable
Junction_4
    -> Tester_2
Note: This workbench assists in identfiying when new DHS surveys and/or GPS data might be available. / It compares surveys listed as being "available" in the DHS API, and surveys listed there as being "available" whilst having GPS data, with the surveys and GPS data we hold in our DHS database. This doesn't cover everything: for example the API lists surveys as "having GPS" even when the GPS data are permanently embargoed, or alternatively when they are not yet ready. So we maintain an external CSV file listing these known issues to cut down the "false positives this workbench produces.
Note: Get ID numbers of all surveys in our database
SQLCreator
    DATASET = DHS Data Readonly
    EXPOSED_ATTRIBUTE_LIST = surveyid
    FORMAT = POSTGRES
    POSTGRES_NAMED_CONNECTION = DHS Data Readonly
    POSTGRES_QUERY_FEATURE_TYPES_FOR_MERGE_FILTERS = Yes
    POSTGRES_SCHEMAS_FOR_TABLE_LISTING = dhs_survey_specs
    SQL_STATEMENT:
      SELECT distinct (surveyid) from dhs_data_tables."RECH1"
      UNION
      SELECT distinct (surveyid) from dhs_data_tables."REC01"
    RESULT -> FeatureMerger_2 [SUPPLIER]
FeatureMerger_2
    ATTR_ACCUM_MODE = Merge Supplier
    ATTR_CONFLICT_RES = Use Requestor
    IGNORE_NULLS = No
    JOIN_KEYS = @Value(SurveyNum) @Value(surveyid) AUTO
    MERGE_TYPE = Attributes Only
    PROCESS_DUPS = NO
    REJECT_NULL_MISSING_KEYS = No
    SUPPLIERS_FIRST = No
    MERGED -> Survey_Data_Held
    UNMERGED_REQUESTOR -> FeatureMerger_6 [REQUESTOR]
    UNUSED_SUPPLIER -> WARN_Svy_Not_In_API
Survey_Data_Held: Inspector
WARN_Svy_Not_In_API: Inspector
FeatureMerger_6
    ATTR_ACCUM_MODE = Merge Supplier
    ATTR_CONFLICT_RES = Use Requestor
    IGNORE_NULLS = No
    JOIN_KEYS = @Value(SurveyNum) @Value(surveynum) AUTO
    MERGE_TYPE = Attributes Only
    PROCESS_DUPS = NO
    REJECT_NULL_MISSING_KEYS = No
    SUPPLIERS_FIRST = No
    MERGED -> 03_Survey_Data_Known_Issues
    UNMERGED_REQUESTOR -> 02_Probably_New_Survey_Data
    UNMERGED_REQUESTOR -> Potential_New_Surveys (writer XLSXW_1)
03_Survey_Data_Known_Issues: Inspector
FeatureMerger_4
    ATTR_ACCUM_MODE = Merge Supplier
    ATTR_CONFLICT_RES = Use Requestor
    IGNORE_NULLS = No
    JOIN_KEYS = @Value(SurveyNum) @Value(SurveyNum) AUTO
    MERGE_TYPE = Attributes Only
    PROCESS_DUPS = No
    REJECT_NULL_MISSING_KEYS = No
    SUPPLIERS_FIRST = No
    MERGED -> 01_Potentially_New_GPS_Data
    MERGED -> Potential_New_GPS_Data (writer XLSXW_1)

Bookmark: Get all survey IDs
Note: Previously we could just use a CSV reader on the API URL. However they now seem to have implemented a max per page of 100 surveys (regardless of perpage setting) and there are currently ~424 surveys. Adjust the number of features created here if more pages are needed. Pre-configured the attributes on the reader from the dayz when we used a normal reader, so don't worry about the apparently broken attribs unless they change them.
Creator_3
    GEOMTYPE = Geometry Object
    NUM = 10
    CREATED -> Counter
Counter
    CNT_ATTR = pagenum
    DOMAIN = counter
    SCOPE = Global
    START = 1
    -> AttributeManager_3
AttributeManager_3
    ATTR_TABLE = SET_TO _api_survey_list_URL = http://api.dhsprogram.com/rest/dhs/surveys?f=csv&page=@Value(pagenum)
    -> FeatureReader [INITIATOR]
Note: Expose only the attribs we need here
FeatureReader
    ATTRS_TO_EXPOSE = SurveyId SurveyNum ReleaseDate SurveyCharacteristicIds CountryName RegionName
    ATTR_ACCUM_MODE = Merge Initiator and Result
    ATTR_CONFLICT_RES = Use Result
    COMBINE_GEOM = Use Result
    CSV2_CASE_SENSITIVE_FIELD_NAMES = Yes
    CSV2_DATA_START_LINE = 2
    CSV2_DELIMITER = auto
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 1000
    CSV2_SCAN_TYPES = No
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = @Value(_api_survey_list_URL)
    FORMAT = CSV2
    INTERACT = <No Spatial Filter>
    OUTPUT_FEATURES_DISPLAY = Schema and Data Features
    <OTHER> -> FeatureMerger [SUPPLIER]
    <OTHER> -> All_Surveys_In_API
    <OTHER> -> FeatureMerger_2 [REQUESTOR]
    <OTHER> -> Junction
    <OTHER> -> Tester_3
    <REJECTED> -> blank_pages
All_Surveys_In_API: Inspector
Note: Query the DHS API to get the ID numbers and other properties, including whether they have GPS data, of all surveys flagged in the API as "available" (default if surveyStatus is not specified) 313
Note: Would be a faff to work out num pages in advance so just read extra and discard the rejected requests
blank_pages: Inspector
Note: FeatureMerger_4 : Supplier
Junction
    -> Junction_2

Bookmark: Filter out the surveys with GPS data
Note: Filter to get the surveys with GPS data (characteristic id = 26). This doesn't mean that the GPS data are actually available; they may be not ready or may be restricted. NB we could filter the API query directly to only return these. 192
Tester_3
    BOOL_OP = OR
    TEST_CLAUSE = CASE_INSENSITIVE_TEST @Value(SurveyCharacteristicIds) CONTAINS 26
    PASSED -> AttributeCreator
    FAILED -> AttributeCreator_2
AttributeCreator
    ATTR_TABLE = SET_TO HasGPS = Yes
    -> All_Surveys_In_DHS_API (writer XLSXW_1)
    -> AttributeKeeper
AttributeKeeper
    KEEP_ATTRS = SurveyNum
    -> FeatureMerger_3 [REQUESTOR]
AttributeCreator_2
    ATTR_TABLE = SET_TO HasGPS = No
    -> All_Surveys_In_DHS_API (writer XLSXW_1)
All_Surveys_In_DHS_API (writer XLSXW_1)
    attributes: SurveyId auto(20), SurveyNum auto(20), ReleaseDate auto(20), CountryName auto(20), RegionName auto(20), HasGPS auto(20)

Bookmark: Get recently-updated surveys
Note: Query the DHS API to get the ID names (and incidentally other properties) of recently-updated surveys. Threshold of "recent" is hardcoded in the AttributeManager for now to 2015-09-01. This API endpoint doesn't return ID numbers, nor info on what was updated.
Creator_2
    GEOMTYPE = Geometry Object
    NUM = 1
    CREATED -> AttributeManager_2
AttributeManager_2
    ATTR_TABLE:
      SET_TO _api_survey_list_URL = http://api.dhsprogram.com/rest/dhs/dataupdates?lastUpdate=20150901&f=csv
      REMOVE _creation_instance
    -> FeatureReader_2 [INITIATOR]
FeatureReader_2
    ATTRS_TO_EXPOSE = SurveyId SurveyYear DHS_CountryCode CountryName UpdateDate
    ATTR_ACCUM_MODE = Merge Initiator and Result
    ATTR_CONFLICT_RES = Use Result
    COMBINE_GEOM = Use Result
    CSV_SCAN_MAX_FEATURES = 1000
    CSV__ALLOW_SPACES_IN_COLUMN_NAMES = yes
    CSV__DUPLICATE_DELIMS = no
    CSV__FIELD_NAMES_AFTER_HEADER = no
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES DataId%Indicator%Value%Precision%DHS_CountryCode%CountryName%SurveyYear%SurveyId%IndicatorId%IndicatorOrder%CharacteristicId%CharacteristicOrder%CharacteristicCategory%CharacteristicLabel%ByVariableId%ByVariableLabel%IsTotal%IsPreferred%SDRID%RegionId%SurveyYearLabel%SurveyType%DenominatorWeighted%DenominatorUnweighted%CILow%CIHigh%Recordcount%Page%TotalPages\"%%\"Filter\"%\"STRING_ENCODED _FILTER_REGEX \"%%\"Invert Filter\"%\"CHECKBOX _FILTER_UNMATCHED yes%no\"%no"
    CSV__GROUP_BY_DATASET = no
    CSV__IN_FIELD_NAMES = YES
    CSV__IN_SEPARATOR = ,
    CSV__SCHEMA = number,7,0,char,31,,number,4,1,number,2,0,char,3,,char,9,,number,5,0,char,10,,char,14,,number,9,0,number,5,0,number,2,0,char,6,,char,6,,number,2,0,char,1,,number,2,0,number,2,0,number,5,0,char,1,,number,5,0,char,4,,number,6,0,number,6,0,char,1,,char,1,,number,2,0,number,2,0,number,2,0
    CSV__SCHEMA_WITH_COL_NAMES = DataId,number,7,0,Indicator,char,31,,Value,number,4,1,Precision,number,2,0,DHS_CountryCode,char,3,,CountryName,char,9,,SurveyYear,number,5,0,SurveyId,char,10,,IndicatorId,char,14,,IndicatorOrder,number,9,0,CharacteristicId,number,5,0,CharacteristicOrder,number,2,0,CharacteristicCategory,char,6,,CharacteristicLabel,char,6,,ByVariableId,number,2,0,ByVariableLabel,char,1,,IsTotal,number,2,0,IsPreferred,number,2,0,SDRID,number,5,0,RegionId,char,1,,SurveyYearLabel,number,5,0,SurveyType,char,4,,DenominatorWeighted,number,6,0,DenominatorUnweighted,number,6,0,CILow,char,1,,CIHigh,char,1,,Recordcount,number,2,0,Page,number,2,0,TotalPages,number,2,0
    CSV__SKIP_FOOTER = 0
    CSV__SKIP_LINES = 1
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES DataId%Indicator%Value%Precision%DHS_CountryCode%CountryName%SurveyYear%SurveyId%IndicatorId%IndicatorOrder%CharacteristicId%CharacteristicOrder%CharacteristicCategory%CharacteristicLabel%ByVariableId%ByVariableLabel%IsTotal%IsPreferred%SDRID%RegionId%SurveyYearLabel%SurveyType%DenominatorWeighted%DenominatorUnweighted%CILow%CIHigh%Recordcount%Page%TotalPages\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__STRIP_QUOTES = yes
    DATASET = @Value(_api_survey_list_URL)
    FORMAT = CSV
    OUTPUT_FEATURES_DISPLAY = Schema and Data Features
    <OTHER> -> FeatureMerger [REQUESTOR]
Note: Merge to get ID number of recently-updated surveys
FeatureMerger
    ATTR_ACCUM_MODE = Merge Supplier
    ATTR_CONFLICT_RES = Use Requestor
    IGNORE_NULLS = No
    JOIN_KEYS = @Value(SurveyId) @Value(SurveyId) AUTO
    MERGE_TYPE = Attributes Only
    PROCESS_DUPS = No
    REJECT_NULL_MISSING_KEYS = No
    SUPPLIERS_FIRST = No
    NOT_MERGED -> API_Says_Updated_Check

Bookmark: Read list of known issues
Note: This CSV should be kept updated
missing_and_unavailable (reader CSV2_1)
    attributes: surveynum string, country string, year string, issue string, data issue string, gps issue string, change expected string, last manual check string
    -> Tester
    -> Junction_3
Note: To main survey filter
Junction_3
    -> Junction_4

Bookmark: Filter list of known GPS issues
Note: Filter survey notes to get surveys where GPS is known unavailable despite existing according to API, to avoid re-checking each time.
Tester
    BOOL_OP = AND
    TEST_CLAUSE:
      TEST @Value(change expected) = no
      TEST @Value(gps issue) != no issue
    PASSED -> AttributeKeeper_2
AttributeKeeper_2
    KEEP_ATTRS = surveynum,change expected,gps issue
    -> FeatureMerger_5 [SUPPLIER]

Bookmark: Filter list of known data issues
Note: Filter survey notes to get surveys where data is known unavailable despite existing according to API e.g. restricted or a country we don't have access to (?)
Tester_2
    BOOL_OP = AND
    TEST_CLAUSE:
      TEST @Value(change expected) = no
      TEST @Value(data issue) != no issue
    PASSED -> AttributeKeeper_3
AttributeKeeper_3
    KEEP_ATTRS = surveynum,change expected,data issue
    -> FeatureMerger_6 [SUPPLIER]

Bookmark: Main Outputs
Note: This output should be checked to see if any can be downloaded and processed. Surveys may appear here even though GPS data aren't yet ready.
02_Probably_New_Survey_Data: Inspector
Potential_New_Surveys (writer XLSXW_1)
    attributes: SurveyNum auto(20), SurveyId auto(20), ReleaseDate auto(20)
Potential_New_GPS_Data (writer XLSXW_1)
    attributes: SurveyNum auto(20), SurveyId auto(20), ReleaseDate auto(20)
Note: This output should be check to see if any can be downloaded and processed. Several surveys are marked with GPS data "not yet available" for several years - they will appear here, too.
01_Potentially_New_GPS_Data: Inspector

Bookmark: Check if we hold the GPS data
Note: Get ID numbers of all survey GPS data in our database
SQLCreator_2
    DATASET = DHS Data Readonly
    EXPOSED_ATTRIBUTE_LIST = surveyid
    FORMAT = POSTGRES
    POSTGRES_NAMED_CONNECTION = DHS Data Readonly
    POSTGRES_QUERY_FEATURE_TYPES_FOR_MERGE_FILTERS = Yes
    POSTGRES_SCHEMAS_FOR_TABLE_LISTING = dhs_survey_specs
    SQL_STATEMENT = SELECT distinct (surveyid) from dhs_data_locations.dhs_cluster_locs
    RESULT -> FeatureMerger_3 [SUPPLIER]
FeatureMerger_3
    ATTR_ACCUM_MODE = Merge Supplier
    ATTR_CONFLICT_RES = Use Requestor
    CLEANING_TOLERANCE = None
    IGNORE_NULLS = No
    JOIN_KEYS = @Value(SurveyNum) @Value(surveyid) AUTO
    MERGE_TYPE = Attributes Only
    PROCESS_DUPS = No
    REJECT_NULL_MISSING_KEYS = No
    SUPPLIERS_FIRST = No
    MERGED -> GPS_Data_Held
    UNMERGED_REQUESTOR -> FeatureMerger_5 [REQUESTOR]
FeatureMerger_5
    ATTR_ACCUM_MODE = Merge Supplier
    ATTR_CONFLICT_RES = Use Requestor
    IGNORE_NULLS = No
    JOIN_KEYS = @Value(SurveyNum) @Value(surveynum) AUTO
    MERGE_TYPE = Attributes Only
    PROCESS_DUPS = NO
    REJECT_NULL_MISSING_KEYS = No
    SUPPLIERS_FIRST = No
    MERGED -> 04_GPS_Data_known_issues
    UNMERGED_REQUESTOR -> FeatureMerger_4 [REQUESTOR]
04_GPS_Data_known_issues: Inspector
GPS_Data_Held: Inspector
