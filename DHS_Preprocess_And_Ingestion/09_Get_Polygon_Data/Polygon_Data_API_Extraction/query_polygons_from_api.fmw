FME workspace query_polygons_from_api.fmw

Parameters:
- DestDataset_ESRISHAPE = .   # Destination Esri Shapefile Folder
- DestDataset_POSTGIS = Admin on MAP-FS1 (DHS instance)   # Connection
- DHS_DB_Connection = Admin on MAP-FS1 (DHS instance)   # DHS DB - with the polygons table

Writers:
- ESRISHAPE_1: ESRISHAPE to $(DestDataset_ESRISHAPE)
- POSTGIS_1: POSTGIS to $(DestDataset_POSTGIS)

Note: Previously the DHS API did not return clean GeoJSON but stacked all features as a list under the Data attribute of a single JSON feature. This bookmark unpacked those data, with the upstream FeatureReader being set to read text line data. As of 2019-02-06 the API seems to be returning proper GeoJSON so the FeatureReader has been set to read GeoJSON and this bookmark disabled.

Bookmark: Read all polygons from the API as geojson
Creator
    GEOMTYPE = Geometry Object
    NUM = 7
    CREATED -> Counter
Note: Seems to be max 1000 per page, there are currently ~3900, adjust the number of features created here if more pages are needed. / ~~We read as text, as the API returns the GeoJSON as an attirbute of a larger JSON structure.~~ / We read as GeoJSON
Counter
    CNT_ATTR = pagenum
    DOMAIN = counter
    SCOPE = Global
    START = 1
    -> AttributeCreator
AttributeCreator
    ATTR_TABLE = SET_TO _jsonurl = http://api.dhsprogram.com/rest/dhs/geometry?f=geojson&perpage=1000&page=@Value(pagenum)
    -> FeatureReader_2 [INITIATOR]
FeatureReader_2
    ATTRS_TO_EXPOSE = text_line_data
    ATTR_ACCUM_MODE = Only Use Result
    COMBINE_GEOM = Use Result
    DATASET = @Value(_jsonurl)
    FORMAT = GEOJSON
    GEOJSON_FLATTEN_MODE = ALL_LEVELS
    GEOJSON_USE_BASENAME_AS_DEFAULT_FEATURE_TYPE = Yes
    GEOJSON_USE_SEARCH_ENVELOPE = NO
    INTERACT = <No Spatial Filter>
    OUTPUT_FEATURES_DISPLAY = Schema and Data Features
    <OTHER> -> JSONFragmenter
    <OTHER> -> AttributeExposer_2
    <REJECTED> -> FeatureReader_2__Rejected_
AttributeExposer_2
    ATTR_LIST = Coordinates,CountryCode,CountryName,RegionID,SurveyId,SurveyType,SurveyYear
    -> FeatureMerger [REQUESTOR]
FeatureReader_2__Rejected_: Inspector

Bookmark: Parse the GeoJSON
Note: The features are all under the JSON "Data" attribute, as as list. Fragment this
JSONFragmenter [off]
    EXPLODE_FORMAT = JSON
    EXTRACT_ATTR = Yes
    JSON_ATTR = text_line_data
    JSON_QUERY = json["features"]
    NEW_ATTRIBUTES = array{}
    RECURSIVE = Yes
    FRAGMENTS -> ListExploder [off]
    <REJECTED> -> JSONFragmenter__Rejected_ [off]
Note: NB I don't think we can just use a GeoJSON feature reader due to the features (the actual GeoJSON) all being stacked under this one Data attribute
ListExploder [off]
    ATTR_ACCUM_MODE = Merge List Attributes
    ATTR_CONFLICT_RES = Use List Attribute Values
    INDEX_ATTR = _element_index
    LIST_ATTR = array{}
    ELEMENTS -> AttributeExposer [off]
AttributeExposer [off]
    ATTR_LIST = Coordinates,CountryCode,CountryName,RegionID,SurveyId,SurveyType,SurveyYear
    -> AttributeRemover [off]
AttributeRemover [off]
    REMOVE_ATTRS = array,json_type,json_index,text_line_data
    -> GeometryReplacer_2 [off]
GeometryReplacer_2 [off]
    KIND_LONG = OGC Well Known Text
    OGC_WKT_PRECISION_DISPLAY = 64-bit
    REMOVE_ATTRIBUTE = Yes
    SOURCE = @Value(Coordinates)
    -> FeatureMerger [REQUESTOR] [off]
    <REJECTED> -> GeometryReplacer_2__Rejected_ [off]
GeometryReplacer_2__Rejected_: Inspector [off]
JSONFragmenter__Rejected_: Inspector [off]

Bookmark: Read all the survey IDs that exist
Creator_2
    GEOMTYPE = Geometry Object
    NUM = 1
    CREATED -> AttributeManager_3
AttributeManager_3
    ATTR_TABLE:
      SET_TO _api_survey_list_URL = http://api.dhsprogram.com/rest/dhs/surveys?f=csv
      REMOVE _creation_instance
    -> FeatureReader [INITIATOR]
FeatureReader
    ATTRS_TO_EXPOSE = SurveyId SurveyNum ReleaseDate
    ATTR_ACCUM_MODE = Merge Initiator and Result
    ATTR_CONFLICT_RES = Use Result
    COMBINE_GEOM = Use Result
    CSV2_CASE_SENSITIVE_FIELD_NAMES = Yes
    CSV2_DATA_START_LINE = 2
    CSV2_DELIMITER = auto
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 1000
    CSV2_SCAN_TYPES = No
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = @Value(_api_survey_list_URL)
    FORMAT = CSV2
    INTERACT = <No Spatial Filter>
    OUTPUT_FEATURES_DISPLAY = Schema and Data Features
    <OTHER> -> FeatureMerger [SUPPLIER]
Note: Merge to get release dates of surveys
FeatureMerger
    ATTR_ACCUM_MODE = Merge Supplier
    ATTR_CONFLICT_RES = Use Requestor
    IGNORE_NULLS = No
    JOIN_KEYS = @Value(SurveyId) @Value(SurveyId) AUTO
    MERGE_TYPE = Attributes Only
    PROCESS_DUPS = No
    REJECT_NULL_MISSING_KEYS = No
    SUPPLIERS_FIRST = No
    MERGED -> FeatureMerger_2 [REQUESTOR]
    NOT_MERGED -> Polygon_From_Unknown_Svy
Polygon_From_Unknown_Svy: Inspector

Bookmark: Check for surveys we already have the polygons for
Note: Get survey IDs with polygons / already in the database. For now we just skip iif any exist, rather than checking they're in sync at any more specific level
SQLCreator
    DATASET = $(DHS_DB_Connection)
    EXPOSED_ATTRIBUTE_LIST = surveyid
    FORMAT = POSTGIS
    POSTGIS_DISABLE_COLLECTION_SPLITTING = yes
    POSTGIS_NAMED_CONNECTION = $(DHS_DB_Connection)
    POSTGIS_QUERY_FEATURE_TYPES_FOR_MERGE_FILTERS = Yes
    POSTGIS_SCHEMAS_FOR_TABLE_LISTING = dhs_data_locations
    POSTGIS_USE_TRUE_POSTGIS_TYPES = yes
    SQL_STATEMENT = select distinct surveyid from dhs_data_locations.dhs_survey_polygons
    RESULT -> AttributeCreator_3
AttributeCreator_3
    ATTR_TABLE = SET_TO _alreadyGot = 1
    -> FeatureMerger_2 [SUPPLIER]
FeatureMerger_2
    ATTR_ACCUM_MODE = Merge Supplier
    ATTR_CONFLICT_RES = Use Requestor
    CLEANING_TOLERANCE = None
    IGNORE_NULLS = No
    JOIN_KEYS = @Value(SurveyNum) @Value(surveyid) AUTO
    MERGE_TYPE = Attributes Only
    PROCESS_DUPS = No
    REJECT_NULL_MISSING_KEYS = No
    SUPPLIERS_FIRST = No
    MERGED -> CoordinateSystemSetter
    UNMERGED_REQUESTOR -> CoordinateSystemSetter

Bookmark: Write them to the DB and also a shapespacefile
Note: We will write "new" polygons to the DB, and all polygons to a shapespacefile
CoordinateSystemSetter
    COORDSYS = EPSG:4326
    -> AttributeManager
AttributeManager
    ATTR_TABLE:
      REMOVE _element_index
      RENAME_SET_VALUE CountryCode > country_code
      RENAME_SET_VALUE CountryName > country_name
      RENAME_SET_VALUE RegionID > regionid
      RENAME_SET_VALUE SurveyId > survey_code
      RENAME_SET_VALUE SurveyType > survey_type
      RENAME_SET_VALUE SurveyYear > survey_year
      REMOVE _api_survey_list_URL
      RENAME_SET_VALUE SurveyNum > surveyid
      RENAME_SET_VALUE ReleaseDate > release_date
    -> Tester
    -> AttributeCreator_2
Tester
    BOOL_OP = OR
    TEST_CLAUSE:
      TEST @Value(_alreadyGot) != 1
      TEST _alreadyGot ATTRIBUTE_IS_MISSING ""
    PASSED -> dhs_survey_polygons (writer POSTGIS_1)
dhs_survey_polygons (writer POSTGIS_1)
    attributes: country_code varchar(5), country_name varchar(30), regionid varchar(30), survey_code varchar(20), survey_type varchar(15), survey_year int4, surveyid int4, release_date varchar(20)
AttributeCreator_2
    ATTR_TABLE = SET_TO today = dhs_polygons_@DateTimeFormat(@DateTimeNow(),%Y%m%d)
    -> dhs_polygons_20170704 (writer ESRISHAPE_1)
dhs_polygons_20170704 (writer ESRISHAPE_1)
    attributes: country_co char(5), country_na char(30), regionid char(30), survey_cod char(20), survey_typ char(15), survey_yea long, surveyid long, release_da char(20)
