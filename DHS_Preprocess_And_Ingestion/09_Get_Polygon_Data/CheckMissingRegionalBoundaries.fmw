FME workspace CheckMissingRegionalBoundaries.fmw

Parameters:
- DHS_Survey_Listing_API = http://api.dhsprogram.com/rest/dhs/surveys?f=csv   # CSV retrieved from DHS API listing survey info - use API endpoint or local file

Readers:
- CSV2_1: CSV2 from $(DHS_Survey_Listing_API)

Note: Ones for which we have full data from the SDR
SQLCreator
    DATASET = Admin on MAP-FS1 (DHS instance)
    EXPOSED_ATTRIBUTE_LIST = surveyid_sdr
    FORMAT = POSTGRES
    POSTGRES_NAMED_CONNECTION = Admin on MAP-FS1 (DHS instance)
    POSTGRES_QUERY_FEATURE_TYPES_FOR_MERGE_FILTERS = Yes
    POSTGRES_READ_TIME_WITH_TIMEZONE = Yes
    SQL_STATEMENT = select distinct svyid as surveyid_sdr from dhs_data_locations.dhs_sdr_survey_polygons
    RESULT -> FeatureMerger_3 [SUPPLIER]
Note: Ones for which we have the limited data from the API
SQLCreator_2
    DATASET = Admin on MAP-FS1 (DHS instance)
    EXPOSED_ATTRIBUTE_LIST = surveyid_api
    FORMAT = POSTGRES
    POSTGRES_NAMED_CONNECTION = Admin on MAP-FS1 (DHS instance)
    POSTGRES_QUERY_FEATURE_TYPES_FOR_MERGE_FILTERS = Yes
    POSTGRES_READ_TIME_WITH_TIMEZONE = Yes
    SQL_STATEMENT = select distinct surveyid as surveyid_api from dhs_data_locations.dhs_api_survey_polygons
    RESULT -> FeatureMerger_4 [SUPPLIER]
Note: Current list of all avail surveys from the API
Note: Builds a list of survey IDs for which we do not have regional polygon data. This can be used to see if the data now exist (hint: they probably still don't) on the DHS SDR website, either manually or via the geoprocessing service at https://gis.dhsprogram.com/arcgis/rest/services/Tools/DownloadSubnationalData/GPServer/downloadSubNationalBoundaries/submitJob
CSV (reader CSV2_1)
    attributes: SurveyId string, DHS_CountryCode string, SurveyYear string, SurveyType string, SurveyStatus string, CountryName string, SurveyYearLabel string, SurveyNum string, IndicatorData string, RegionName string, SubregionName string, PublicationDate string, ReleaseDate string, SurveyCharacteristicIds string, Footnotes string, FieldworkStart string, FieldworkEnd string, ImplementingOrg string, NumberOfSamplePoints string, NumberofHouseholds string, UniverseOfWomen string, NumberOfWomen string, MinAgeWomen string, MaxAgeWomen string, UniverseOfMen string, NumberOfMen string, MinAgeMen string, MaxAgeMen string, NumberOfFacilities string
    -> FeatureMerger_3 [REQUESTOR]
    -> FeatureMerger_4 [REQUESTOR]
FeatureMerger_3
    ATTR_ACCUM_MODE = Merge Supplier
    ATTR_CONFLICT_RES = Use Requestor
    IGNORE_NULLS = No
    JOIN_KEYS = @Value(SurveyId) @Value(surveyid_sdr) AUTO
    MERGE_TYPE = Attributes Only
    PROCESS_DUPS = NO
    REJECT_NULL_MISSING_KEYS = No
    SUPPLIERS_FIRST = No
    UNMERGED_REQUESTOR -> FeatureMerger_3_UnmergedRequestor
FeatureMerger_3_UnmergedRequestor: Inspector
FeatureMerger_4
    ATTR_ACCUM_MODE = Merge Supplier
    ATTR_CONFLICT_RES = Use Requestor
    IGNORE_NULLS = No
    JOIN_KEYS = @Value(SurveyId) @Value(surveyid_api) AUTO
    MERGE_TYPE = Attributes Only
    PROCESS_DUPS = NO
    REJECT_NULL_MISSING_KEYS = No
    SUPPLIERS_FIRST = No
    UNMERGED_REQUESTOR -> FeatureMerger_4_UnmergedRequestor
FeatureMerger_4_UnmergedRequestor: Inspector
