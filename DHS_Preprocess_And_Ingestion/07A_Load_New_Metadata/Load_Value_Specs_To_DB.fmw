FME workspace Load_Value_Specs_To_DB.fmw

Parameters:
- ValueSpecCSVs = D:\InformalCities\DHS\staging\parsed_specs\*.FlatValuesSpec.csv   # Parsed value spec csv file(s)
- DestDataset_POSTGRES = DHS admin @ local docker   # Connection
- RecordSpecCSVs = D:\InformalCities\DHS\staging\parsed_specs\*.FlatRecordSpec.csv   # Parsed record spec csv file(s)
- DestDataset_POSTGRES_5 = DHS admin @ local docker   # Connection

Readers:
- CSV2_1: CSV2 from $(ValueSpecCSVs)
- CSV2_2: CSV2 from $(RecordSpecCSVs)

Writers:
- POSTGRES_1: POSTGRES to $(DestDataset_POSTGRES)
- POSTGRES_2: POSTGRES to $(DestDataset_POSTGRES_5)

ValuesAlreadyPresent: Inspector [off]
Note: After parsing the .DCF files to a FlatRecordSpec and FlatValueSpec file, use this workbench to load them into the database if they are not already present
dhs_value_descs (writer POSTGRES_1)
    attributes: col_name varchar(20), value varchar(20), value_desc varchar(200), value_type varchar(20), surveyid varchar(4)

Bookmark: Check and load column value specification files
Note: Just dumps all the table and value specs into flat database tables. We have a separate relational structure set up for this schema information but that's not currently in use.
CSV (reader CSV2_1)
    attributes: FileCode string, Name string, Value string, ValueDesc string, ValueType string
    -> StringSearcher
NullAttributeMapper
    ATTRCHOICE = Selected Attributes
    ATTRLIST = value_desc value_type
    NULL_TREATMENT = Null
    SOURCE_ATTR_VAL = Null Empty
    -> dhs_value_descs (writer POSTGRES_1)

Bookmark: Get numeric id and tidy attribs
StringSearcher
    CASE = no
    MATCHED_RESULT_ATTR = surveyid
    REGEXP = ^\d+
    STRING_TO_SEARCH = @Value(FileCode)
    MATCHED -> StringReplacer
StringReplacer
    CASE = NO
    FIND_TEXT = '
    NO_MATCH = _FME_NO_OP_
    REGEXP = NO
    SRC_ATTRS = Value
    -> AttributeTrimmer
AttributeTrimmer
    SRC_ATTRS = ValueDesc,Value
    TRIM_TO_NONE = Yes
    TRIM_TYPE = Both
    -> FeatureMerger_3 [REQUESTOR]

Bookmark: Check and load table column specification files
CSV (reader CSV2_2)
    attributes: ItemType string, FileCode string, RecordName string, RecordTypeValue string, RecordLabel string, Name string, Label string, Start string, Len string, Occurrences string, ZeroFill string, DecimalChar string, Decimal string, FMETYPE string
    -> Tester_2
Tester_2
    BOOL_OP = AND
    TEST_CLAUSE:
      TEST @Value(RecordLabel) != *
      TEST @Value(RecordName) != *
    TEST_MODE = TEST
    PASSED -> BulkAttributeRenamer
AttributeCreator
    ATTR_TABLE = SET_TO fme_db_operation = UPDATE
    -> dhs_table_specs_flat (writer POSTGRES_2)
dhs_table_specs_flat (writer POSTGRES_2)
    attributes: itemtype varchar(17), recordname varchar(20), recordtypevalue varchar(4), recordlabel varchar(85), name varchar(20), label varchar(200), start int2, len int2, fmetype varchar(13), surveyid varchar(4)

Bookmark: Get numeric id and tidy attribs
BulkAttributeRenamer
    ATTRCHOICE = All Attributes
    CASE_CHANGE_TYPE = lower
    MODE_CHOICE = RENAME
    PATTERN_ACTION_DISP = CASECHANGE
    -> StringSearcher_2
StringSearcher_2
    CASE = no
    MATCHED_RESULT_ATTR = surveyid
    REGEXP = ^\d+
    STRING_TO_SEARCH = @Value(filecode)
    MATCHED -> FeatureMerger_2 [REQUESTOR]

Bookmark: See if survey is present in values table
SQLCreator_2
    DATASET = DHS admin @ local docker
    EXPOSED_ATTRIBUTE_LIST = surveyid
    FORMAT = POSTGRES
    POSTGRES_CREATE_FEATURE_TABLES_FROM_DATA = Yes
    POSTGRES_NAMED_CONNECTION = DHS admin @ local docker
    POSTGRES_QUERY_FEATURE_TYPES_FOR_MERGE_FILTERS = Yes
    POSTGRES_READ_TIME_WITH_TIMEZONE = Yes
    SQL_STATEMENT = select distinct surveyid from dhs_survey_specs.dhs_value_descs
    RESULT -> FeatureMerger_3 [SUPPLIER]
FeatureMerger_3
    ATTR_ACCUM_MODE = Merge Supplier
    ATTR_CONFLICT_RES = Use Requestor
    IGNORE_NULLS = No
    JOIN_KEYS = @Value(surveyid) @Value(surveyid) AUTO
    MERGE_TYPE = Attributes Only
    PROCESS_DUPS = NO
    REJECT_NULL_MISSING_KEYS = No
    SUPPLIERS_FIRST = Yes
    MERGED -> Sampler
    MERGED -> FeatureMerger [REQUESTOR]
    UNMERGED_REQUESTOR -> AttributeManager

Bookmark: If survey already present, check individual cols
Sampler
    GROUP_BY = surveyid
    RATE = 1
    SAMPLE_MODE = No
    SAMPLE_TYPE_LONG = First N Features
    SAMPLED -> AttributeKeeper
AttributeKeeper
    CREATE_BULK_MODE_FEATURES = No
    KEEP_ATTRS = surveyid
    -> SQLExecutor_2 [INITIATOR]
SQLExecutor_2
    COMBINE_ATTRS = Keep Initiator Attributes if Conflict
    COMBINE_GEOM = Initiator Geometry Only
    DATASET = DHS admin @ local docker
    EXPOSED_ATTRIBUTE_LIST = col_name
    FORMAT = POSTGIS
    POSTGIS_CREATE_FEATURE_TABLES_FROM_DATA = Yes
    POSTGIS_DISABLE_COLLECTION_SPLITTING = yes
    POSTGIS_NAMED_CONNECTION = DHS admin @ local docker
    POSTGIS_QUERY_FEATURE_TYPES_FOR_MERGE_FILTERS = Yes
    POSTGIS_READ_TIME_WITH_TIMEZONE = Yes
    POSTGIS_USE_TRUE_POSTGIS_TYPES = yes
    SQL_STATEMENT = SELECT distinct col_name FROM dhs_survey_specs.dhs_value_descs WHERE surveyid = '@Value(surveyid)'
    RESULT -> FeatureMerger [SUPPLIER]
FeatureMerger
    ATTR_ACCUM_MODE = Merge Supplier
    ATTR_CONFLICT_RES = Use Requestor
    GROUP_BY = surveyid
    IGNORE_NULLS = No
    JOIN_KEYS = @Value(surveyid) @Value(surveyid) AUTO @Value(Name) @Value(col_name) AUTO
    MERGE_TYPE = Attributes Only
    PROCESS_DUPS = NO
    REJECT_NULL_MISSING_KEYS = No
    SUPPLIERS_FIRST = No
    MERGED -> ValuesAlreadyPresent [off]
    UNMERGED_REQUESTOR -> AttributeManager

Bookmark: Load new survey / col values
AttributeManager
    ATTR_TABLE:
      REMOVE FileCode
      RENAME_SET_VALUE Name > col_name
      RENAME_SET_VALUE Value > value
      RENAME_SET_VALUE ValueDesc > value_desc
      RENAME_SET_VALUE ValueType > value_type
    -> NullAttributeMapper

Bookmark: See if survey is present in, err, tables table
SQLCreator
    DATASET = DHS admin @ local docker
    EXPOSED_ATTRIBUTE_LIST = surveyid
    FORMAT = POSTGRES
    POSTGRES_CREATE_FEATURE_TABLES_FROM_DATA = Yes
    POSTGRES_NAMED_CONNECTION = DHS admin @ local docker
    POSTGRES_QUERY_FEATURE_TYPES_FOR_MERGE_FILTERS = Yes
    POSTGRES_READ_TIME_WITH_TIMEZONE = Yes
    SQL_STATEMENT = select distinct surveyid from dhs_survey_specs.dhs_table_specs_flat
    RESULT -> FeatureMerger_2 [SUPPLIER]
FeatureMerger_2
    ATTR_ACCUM_MODE = Merge Supplier
    ATTR_CONFLICT_RES = Use Requestor
    IGNORE_NULLS = No
    JOIN_KEYS = @Value(surveyid) @Value(surveyid) AUTO
    MERGE_TYPE = Attributes Only
    PROCESS_DUPS = NO
    REJECT_NULL_MISSING_KEYS = No
    SUPPLIERS_FIRST = Yes
    MERGED -> SQLExecutor [INITIATOR]
    UNMERGED_REQUESTOR -> AttributeCreator_2

Bookmark: If survey already present, check individual cols
Note: Maybe we've added a table we didn't download originally such as male-recode tables
SQLExecutor
    COMBINE_ATTRS = Result Attributes Only
    COMBINE_GEOM = Initiator Geometry Only
    DATASET = DHS admin @ local docker
    FORMAT = POSTGRES
    POSTGRES_CREATE_FEATURE_TABLES_FROM_DATA = Yes
    POSTGRES_NAMED_CONNECTION = DHS admin @ local docker
    POSTGRES_QUERY_FEATURE_TYPES_FOR_MERGE_FILTERS = Yes
    POSTGRES_READ_TIME_WITH_TIMEZONE = Yes
    SQL_STATEMENT:
      select name from dhs_survey_specs.dhs_table_specs_flat
      where
      surveyid = '@Value(surveyid)'
      AND
      recordname = '@Value(recordname)'
      AND
      name = '@Value(name)'
    INITIATOR -> Tester
Tester
    BOOL_OP = OR
    TEST_CLAUSE = TEST @Value(_matched_records) = 0
    TEST_MODE = TEST
    PASSED -> AttributeCreator_2
    FAILED -> AttributeCreator
AttributeCreator_2
    ATTR_TABLE = SET_TO fme_db_operation = INSERT
    -> dhs_table_specs_flat (writer POSTGRES_2)
