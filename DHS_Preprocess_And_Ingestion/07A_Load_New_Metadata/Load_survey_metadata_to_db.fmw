FME workspace Load_survey_metadata_to_db.fmw

Parameters:
- DestDataset_POSTGRES = DHS admin @ local docker   # Connection
- SourceDataset_CSV2 = http://api.dhsprogram.com/rest/dhs/surveys?f=csv&surveyStatus=all&perpage=2000   # Source CSV (Comma Separated Value) File(s)

Readers:
- CSV2_1: CSV2 from $(SourceDataset_CSV2)

Writers:
- POSTGRES_1: POSTGRES to $(DestDataset_POSTGRES)

Note: This just dumps an up-to-date listing of the surveys to the metadata table in the database
Creator
    GEOMTYPE = Geometry Object
    NUM = 10
    CREATED -> Counter
Counter
    CNT_ATTR = pagenum
    DOMAIN = counter
    SCOPE = Global
    START = 1
    -> AttributeCreator
AttributeCreator
    ATTR_TABLE = SET_TO _csvurl = http://api.dhsprogram.com/rest/dhs/surveys?f=csv&surveyStatus=all&page=@Value(pagenum)
    -> FeatureReader_2 [INITIATOR]
FeatureReader_2
    ATTR_ACCUM_MODE = Only Use Result
    COMBINE_GEOM = Use Result
    CSV2_CASE_SENSITIVE_FIELD_NAMES = Yes
    CSV2_DATA_START_LINE = 2
    CSV2_DELIMITER = auto
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 1000
    CSV2_SCAN_TYPES = No
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = @Value(_csvurl)
    FORMAT = CSV2
    INTERACT = <No Spatial Filter>
    OUTPUT_FEATURES_DISPLAY = Schema and Data Features
    <OTHER> -> BulkAttributeRenamer
    <REJECTED> -> blank_pages
BulkAttributeRenamer
    ATTRCHOICE = All Attributes
    CASE_CHANGE_TYPE = lower
    MODE_CHOICE = RENAME
    PATTERN_ACTION_DISP = CASECHANGE
    -> dhs_survey_listing (writer POSTGRES_1)
dhs_survey_listing (writer POSTGRES_1)
    attributes: surveyid text, dhs_countrycode text, surveyyear text, surveytype text, surveystatus text, countryname text, surveyyearlabel text, surveynum text, indicatordata text, regionname text, subregionname text, publicationdate text, releasedate text, surveycharacteristicids text, footnotes text, fieldworkstart text, fieldworkend text, implementingorg text, numberofsamplepoints text, numberofhouseholds text, universeofwomen text, numberofwomen text, minagewomen text, maxagewomen text, universeofmen text, numberofmen text, minagemen text, maxagemen text, numberoffacilities text
Note: Would be a faff to work out num pages in advance so just read extra and discard the rejected requests
blank_pages: Inspector
Note: Previously we could just use a CSV reader on the API URL. However they now seem to have implemented a max per page of 100 surveys (regardless of perpage setting) and there are currently ~424 surveys. Adjust the number of features created here if more pages are needed. Pre-configured the attributes on the reader from the dayz when we used a normal reader, so don't worry about the apparently broken attribs unless they change them.
CSV (reader CSV2_1) [off]
    attributes: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
