FME workspace Load_DHS_Data_To_PG_With_Checks.fmw

Parameters:
- SourceDataset_PATH = C:\Users\zool1301\Documents\02_Update_Staging_Template\tables   # Source Folder and File Pathnames Folder
- DestDataset_POSTGRES = DHS Data admin   # Connection
- SourceDataset_FFS_3 = \\map-fs1.ndph.ox.ac.uk\map_data\DHS_Automation\Acquisition\Update_Logs\20181107_Updates\AlSchemas_To_20181107.ffs   # Source FME Feature Store (FFS) File(s)
- SourceDataset_CSV2 = G:\Shared drives\dhs-outputs\DHS_Acquisition_And_Ingestion\01a_Update_Logs\New_Table_Columns_By_Survey.csv   # Source CSV (Comma Separated Value) File(s)
- Force_Reload_Existing = 0   # Reload surveys that appear to be complete in DB, e.g. if data values have changed
- Load_New_Tables = 1   # Load CSVs which don't even have a table yet
- DestDataset_POSTGRES_3 = DHS Data admin   # Connection

Readers:
- PATH_1: PATH from $(SourceDataset_PATH)
- FFS_1: FFS from $(SourceDataset_FFS_3)
- CSV2_1: CSV2 from $(SourceDataset_CSV2)

Writers:
- POSTGRES_1: POSTGRES to $(DestDataset_POSTGRES)
- POSTGRES_2: POSTGRES to $(DestDataset_POSTGRES_3)

Note: Read the names of all the survey CSV tables in this update, generated using the parser code
PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> StringSearcher_3
StringSearcher_3
    CASE = no
    MATCHED_RESULT_ATTR = SurveyID_File
    REGEXP = ^\d+
    STRING_TO_SEARCH = @Value(path_filename)
    MATCHED -> StringSearcher_2
StringSearcher_2
    CASE = no
    MATCHED_RESULT_ATTR = RecordName_File
    REGEXP = M?REC[0-9A-Z]{2,4}
    STRING_TO_SEARCH = @Value(path_filename)
    MATCHED -> Matcher
    NOT_MATCHED -> Duplicate_Tbl_File_Skipped
Note: Is it that stupid survey 156 with lots of copies of each table?
Matcher
    BLANK_AND_MISSING_DIFFER = No
    CNT_ATTR = _match_id
    LENIENT_MATCH = No
    MATCH = 2D
    MATCHATTRS = RecordName_File SurveyID_File
    MATCH_STRATEGY = Match Selected Attributes
    MATCHED -> Duplicate_Tbl_File_Skipped
    NOT_MATCHED -> Files_To_Check
    NOT_MATCHED -> FeatureMerger [REQUESTOR]
Files_To_Check: Inspector
Duplicate_Tbl_File_Skipped: Inspector
Note: Collate all the files we want to load. / Remember these are just paths, not the actual data
AttributeKeeper
    KEEP_ATTRS = surveyid,path_windows,table_name
    -> FeatureMerger_3 [REQUESTOR]
Note: Get the schema of the table this file goes into: any one file (survey) for a given table may not have all the attribs needed, so load the schema separately. Also drop any CSVs we have chosen to skip below.
FeatureMerger_3
    ATTR_ACCUM_MODE = Merge Supplier
    ATTR_CONFLICT_RES = Use Requestor
    IGNORE_NULLS = No
    JOIN_KEYS = @Value(table_name) @Value(RecordName) AUTO
    MERGE_TYPE = Attributes Only
    PROCESS_DUPS = No
    REJECT_NULL_MISSING_KEYS = No
    SUPPLIERS_FIRST = No
    MERGED -> Tester_5
    NOT_MERGED -> Schema_Search_Error
Tester_5
    BOOL_OP = AND
    TEST_CLAUSE:
      TEST @Value(_is_json) = 0
      TEST @Value(table_name) != RECH4
    PASSED -> FeatureReader [INITIATOR]
    PASSED -> Files_To_Load_Normal
    FAILED -> AttributeManager_5
    FAILED -> Files_To_Load_JSON
Schema_Search_Error: Inspector

Bookmark: Identify which tables are stored as JSONB
SQLCreator_2 [off]
    DATASET = DHS Data Readonly
    EXPOSED_ATTRIBUTE_LIST = column_name,data_type,table_name
    FORMAT = POSTGRES
    POSTGRES_NAMED_CONNECTION = DHS Data Readonly
    POSTGRES_QUERY_FEATURE_TYPES_FOR_MERGE_FILTERS = Yes
    POSTGRES_READ_TIME_WITH_TIMEZONE = Yes
    SQL_STATEMENT:
      SELECT table_name, column_name, data_type from information_schema.columns
      WHERE
      column_name='data'
      AND data_type='jsonb'
    RESULT -> FeatureMerger_5 [SUPPLIER]
FeatureMerger_5 [off]
    ATTR_ACCUM_MODE = Merge Supplier
    ATTR_CONFLICT_RES = Use Requestor
    IGNORE_NULLS = No
    JOIN_KEYS = @Value(RecordName) @Value(table_name) AUTO
    MERGE_TYPE = Attributes Only
    PROCESS_DUPS = NO
    REJECT_NULL_MISSING_KEYS = No
    SUPPLIERS_FIRST = No
    MERGED -> FeatureMerger_5_Merged
    UNMERGED_REQUESTOR -> FeatureMerger_5_UnmergedRequestor
    UNUSED_SUPPLIER -> FeatureMerger_5_UnusedSupplier
FeatureMerger_5_Merged: Inspector [off]
FeatureMerger_5_UnmergedRequestor: Inspector [off]
FeatureMerger_5_UnusedSupplier: Inspector [off]

Bookmark: REDUNDANT - load table schema info from file store
Note: Read the schemas of all the CSV files. This was pre-generated in a separate workbench
AllSchemas_20170410 (reader FFS_1) [off]
    attributes: RecordName varchar(7), attribute{}.name varchar(200), attribute{}.fme_data_type varchar(200), attribute{}.StartMin varchar(200)
    -> AttributeCreator [off]
AttributeCreator [off]
    ATTR_LIST = qualtablename,dhs_data_tables.@Value(RecordName)
    -> ListElementCounter [off]
ListElementCounter [off]
    CNT_ATTR = _column_count
    LIST_NAME = attribute{}
    -> Tester [off]
    -> FeatureMerger_5 [REQUESTOR]
Note: For tables with unwieldy schemas, we don't create them as is. We load them as JSONB data instead. The tables were first created as
Tester [off]
    BOOL_OP = AND
    TEST_CLAUSE = TEST @Value(_column_count) <= 1600
    PASSED -> Normal_Tables [off]
    FAILED -> JSON_Tables [off]
Normal_Tables: Inspector [off]
JSON_Tables: Inspector [off]

Bookmark: Get the schema of the data tables
SQLCreator_3
    DATASET = DHS Data Readonly
    EXPOSED_ATTRIBUTE_LIST = character_maximum_length,column_name,data_type,ordinal_position,table_name,table_schema
    FORMAT = POSTGRES
    POSTGRES_NAMED_CONNECTION = DHS Data Readonly
    POSTGRES_QUERY_FEATURE_TYPES_FOR_MERGE_FILTERS = Yes
    POSTGRES_READ_TIME_WITH_TIMEZONE = Yes
    SQL_STATEMENT:
      SELECT table_schema, table_name, column_name, data_type, character_maximum_length, ordinal_position
      FROM information_schema.columns
      WHERE table_schema = 'dhs_data_tables'
    RESULT -> Sorter
Sorter
    SORT_PARM = table_name ALPHA ASCENDING ordinal_position NUMERIC ASCENDING
    SORTED -> Tester_4
Tester_4
    BOOL_OP = OR
    TEST_CLAUSE = TEST @Value(data_type) = character varying
    PASSED -> AttributeManager
    FAILED -> AttributeManager_2
Note: We read the schema of the existing data tables and use it for two things / - to identify which tables are stored as jsonb and should be packed / - to get the schema information that the writer needs to use "Dynamic Schema" mode and thus write many different tables in one go. / We need the schemas as they exist in the DB, not that of the incoming files, which will only have a subset of the attributes.
AttributeManager
    ATTR_TABLE:
      SET_TO fme_data_type = fme_varchar(@Value(character_maximum_length))
      REMOVE character_maximum_length
      RENAME_SET_VALUE column_name > name
      REMOVE data_type
      RENAME_SET_VALUE table_name > RecordName
      SET_TO _qual_tbl_name = @Value(table_schema).@Value(RecordName)
      REMOVE table_schema
      REMOVE ordinal_position
    -> ListBuilder
AttributeManager_2
    ATTR_TABLE:
      SET_TO fme_data_type = fme_json
      REMOVE character_maximum_length
      RENAME_SET_VALUE column_name > name
      REMOVE data_type
      RENAME_SET_VALUE table_name > RecordName
      SET_TO _qual_tbl_name = @Value(table_schema).@Value(RecordName)
      REMOVE table_schema
      REMOVE ordinal_position
    -> ListBuilder
Note: the dynamic writer needs a list called attribute{} giving the name and type of the columns
ListBuilder
    GROUPS_ORDERED = No
    GROUP_BY = RecordName _qual_tbl_name
    LIST_ATTRS_TO_INCLUDE = fme_data_type name
    LIST_NAME = attribute
    -> ListSearcher
    -> ListBuilder_Output
ListBuilder_Output: Inspector
ListSearcher
    ATTR_VALUE = fme_json
    INDEX_ATTR = _list_index
    LIST_ATTR = attribute{}.fme_data_type
    SEARCH_TYPE = First exact match
    FOUND -> AttributeManager_3
    NOT_FOUND -> AttributeManager_4
AttributeManager_4
    ATTR_TABLE = SET_TO _is_json = 0
    -> FeatureMerger_3 [SUPPLIER]
AttributeManager_3
    ATTR_TABLE = SET_TO _is_json = 1
    -> FeatureMerger_3 [SUPPLIER]

Bookmark: See what surveys are already in DB and how many rows
Note: Get the names of tables that have alrady been created
SQLCreator
    DATASET = DHS Data Readonly
    EXPOSED_ATTRIBUTE_LIST = table_name
    FORMAT = POSTGRES
    POSTGRES_NAMED_CONNECTION = DHS Data Readonly
    POSTGRES_QUERY_FEATURE_TYPES_FOR_MERGE_FILTERS = Yes
    POSTGRES_SCHEMAS_FOR_TABLE_LISTING = dhs_data_tables
    SQL_STATEMENT:
      SELECT table_name
      FROM information_schema.tables
      WHERE table_schema = 'dhs_data_tables'
      -- table_name LIKE '%REC%'
    RESULT -> SQLExecutor_2 [INITIATOR]
    RESULT -> FeatureMerger [SUPPLIER]
    <REJECTED> -> Terminator
Terminator
    MESSAGE = Translation Terminated

Bookmark: Check if the CSV has been at least partly loaded
Note: Get the number of rows already existing for each survey in the DB table
SQLExecutor_2
    COMBINE_ATTRS = Keep Result Attributes if Conflict
    COMBINE_GEOM = Initiator Geometry Only
    DATASET = DHS Data Readonly
    EXPOSED_ATTRIBUTE_LIST = surveyid,nrows_db
    FORMAT = POSTGRES
    POSTGRES_NAMED_CONNECTION = DHS Data Readonly
    POSTGRES_QUERY_FEATURE_TYPES_FOR_MERGE_FILTERS = Yes
    SQL_STATEMENT = SELECT surveyid, count(*) nrows_db FROM dhs_data_tables."@Value(table_name)" GROUP BY surveyid
    RESULT -> FeatureMerger_2 [SUPPLIER]
Note: Has this particualr survey table been loaded even partially?
FeatureMerger_2
    ATTR_ACCUM_MODE = Merge Supplier
    ATTR_CONFLICT_RES = Use Requestor
    IGNORE_NULLS = No
    JOIN_KEYS = @Value(SurveyID_File) @Value(surveyid) AUTO @Value(RecordName_File) @Value(table_name) AUTO
    MERGE_TYPE = Attributes Only
    PROCESS_DUPS = No
    REJECT_NULL_MISSING_KEYS = No
    SUPPLIERS_FIRST = Yes
    MERGED -> PythonCaller
    NOT_MERGED -> File_Not_Yet_In_Table
    NOT_MERGED -> AttributeCopier
Note: Disable this connection to skip reloading files that are already partially loaded
File_Not_Yet_In_Table: Inspector

Bookmark: Check if the CSV's table exists in the DB
Note: Does this table already exist?
FeatureMerger
    ATTR_ACCUM_MODE = Merge Supplier
    ATTR_CONFLICT_RES = Use Requestor
    IGNORE_NULLS = No
    JOIN_KEYS = @Value(RecordName_File) @Value(table_name) AUTO
    MERGE_TYPE = Attributes Only
    PROCESS_DUPS = No
    REJECT_NULL_MISSING_KEYS = No
    SUPPLIERS_FIRST = Yes
    MERGED -> FeatureMerger_2 [REQUESTOR]
    NOT_MERGED -> Tester_3
    NOT_MERGED -> Table_Not_Yet_Begun
Table_Not_Yet_Begun: Inspector
Tester_3
    BOOL_OP = OR
    TEST_CLAUSE = TEST $(Load_New_Tables) = 1
    PASSED -> AttributeCopier

Bookmark: Check for files that have been loaded only partially or which need reloading for some other reason
Note: Countlines in the data CSV
PythonCaller
    NEW_ATTRIBUTES = nrows_file
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              with open (feature.getAttribute('path_windows')) as f:
                  for i,l in enumerate(f):
                      pass
              # nrows will be i+1 but we want to discard 1 (the header)
              feature.setAttribute("nrows_file", i)
              self.pyoutput(feature)
          def close(self):
              pass
    PYTHONSYMBOL = FeatureProcessor
    -> Tester_2
Note: Does the file have the same number of rows as the db? / Or have we chosen to drop-reload regardless, for example if a survey has been re-released with corrected but not new data
Tester_2
    BOOL_OP = AND
    TEST_CLAUSE:
      TEST @Value(nrows_file) = @Value(nrows_db)
      TEST $(Force_Reload_Existing) = 0
    PASSED -> FeatureMerger_4 [REQUESTOR]
    FAILED -> Table_CSV_Needs_Reloading
    FAILED -> SQLExecutor [INITIATOR]
Table_CSV_Needs_Reloading: Inspector
Note: Read the CSV listing new coluimns that have been added (from parsing process)
CSV (reader CSV2_1)
    attributes: maxlen string, name string, recordname string, surveyid string
    -> FeatureMerger_4 [SUPPLIER]
FeatureMerger_4
    ATTR_ACCUM_MODE = Merge Supplier
    ATTR_CONFLICT_RES = Use Requestor
    CLEANING_TOLERANCE = None
    IGNORE_NULLS = No
    JOIN_KEYS = @Value(surveyid) @Value(surveyid) AUTO @Value(RecordName_File) @Value(recordname) AUTO
    MERGE_TYPE = Attributes Only
    PROCESS_DUPS = No
    REJECT_NULL_MISSING_KEYS = No
    SUPPLIERS_FIRST = No
    MERGED -> Table_Needs_Reloading_Due_To_Extra_Cols
    MERGED -> SQLExecutor [INITIATOR]
    UNMERGED_REQUESTOR -> File_Already_Loaded
    <REJECTED> -> Extra_Cols_GT1PerTable
Note: Even if the n rows in the DB is correct, we may also need to reload if there have been extra data columns added for some reason
Table_Needs_Reloading_Due_To_Extra_Cols: Inspector
Note: No ned to do anything
File_Already_Loaded: Inspector
Note: If there's more than one extra column being added to any table this will highlight here - no need to do anything else in particular
Extra_Cols_GT1PerTable: Inspector
Note: Drop data rows from outdated or partly-loaded CSV and rerun it
SQLExecutor
    COMBINE_ATTRS = Keep Initiator Attributes if Conflict
    COMBINE_GEOM = Initiator Geometry Only
    DATASET = DHS Data admin
    FORMAT = POSTGRES
    POSTGRES_NAMED_CONNECTION = Admin on MAP-FS1 (DHS instance)
    POSTGRES_QUERY_FEATURE_TYPES_FOR_MERGE_FILTERS = Yes
    POSTGRES_SCHEMAS_FOR_TABLE_LISTING = dhs_data_tables
    SQL_STATEMENT = DELETE FROM  dhs_data_tables."@Value(table_name)" WHERE surveyid = '@Value(surveyid)'
    INITIATOR -> AttributeKeeper

Bookmark: Prepare for load
Note: Translate the CSV name to table name
AttributeCopier
    ATTR_TABLE:
      COPY RecordName_File > table_name
      COPY SurveyID_File > surveyid
    -> AttributeKeeper

Bookmark: For normal tables: read the actual CSVs and write them to their corresponding tables
Note: The features coming in here basically contain a CSV filename, a list of the attribute names / types of the DB table (of which the CSV file will contain a subset but not necessarily all), and the name of the DB table. The feature reader will read them, and the dynamic DB writer will write them using the schema from the list attribute (which should match how the actual DB table looks)
Files_To_Load_Normal: Inspector
Note: Read the csv file. We don't know here the attributes it will have so they don't show here (and if they did there would be many thousand of them) but the dynamic writer will know what it is looking for.
FeatureReader
    ATTRS_TO_EXPOSE = fme_basename
    ATTR_ACCUM_MODE = Merge Initiator and Result
    ATTR_CONFLICT_RES = Use Result
    COMBINE_GEOM = Use Result
    CSV_SCAN_MAX_FEATURES = 1000
    CSV__ALLOW_SPACES_IN_COLUMN_NAMES = yes
    CSV__DUPLICATE_DELIMS = no
    CSV__FIELD_NAMES_AFTER_HEADER = no
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    CSV__GROUP_BY_DATASET = no
    CSV__IN_FIELD_NAMES = YES
    CSV__IN_SEPARATOR = ,
    CSV__SCHEMA = char,12,,char,6,,char,17,
    CSV__SCHEMA_WITH_COL_NAMES = name,char,12,,RecordName,char,6,,coltype,char,17,
    CSV__SKIP_FOOTER = 0
    CSV__SKIP_LINES = 1
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__STRIP_QUOTES = yes
    DATASET = @Value(path_windows)
    FEATURETYPES_RADIO = FEATURETYPES
    FORMAT = CSV
    OUTPUT_FEATURES_DISPLAY = Based on Connections
    <OTHER> -> NullAttributeMapper
Note: As we're reading from CSVs we have blank strings rather than proper nulls, so convert those. This is crucial for the many-column tables which contain the unioned set of all attribs across all surveys containing that table. Using null rather than empty string ensures all the empty cols only take 1 bit.
NullAttributeMapper
    ATTRCHOICE = All Attributes
    NULL_TREATMENT = Null
    SOURCE_ATTR_VAL = Null Empty
    -> BulkAttributeRenamer_2
BulkAttributeRenamer_2
    ATTRCHOICE = All Attributes
    CASE_CHANGE_TYPE = lower
    MODE_CHOICE = RENAME
    PATTERN_ACTION_DISP = CASECHANGE
    -> Table1 (writer POSTGRES_1)
Table1 (writer POSTGRES_1)

Bookmark: For JSON tables: read the CSVs, pack all except the ID attributes, and write them to their corresponding tables
Files_To_Load_JSON: Inspector
AttributeManager_5
    ATTR_TABLE = RENAME_SET_VALUE path_windows > _CSV_file_name
    -> FeatureReader_2 [INITIATOR]
Note: Read the csv file. We don't know here the attributes it will have so they don't show here but the attribute-json packer will find and pack them nonetheless
FeatureReader_2
    ATTRS_TO_EXPOSE = fme_basename CASEID HHID SQUESTID IXH4
    ATTR_ACCUM_MODE = Merge Initiator and Result
    ATTR_CONFLICT_RES = Use Result
    COMBINE_GEOM = Use Result
    CSV_SCAN_MAX_FEATURES = 1000
    CSV__DUPLICATE_DELIMS = no
    CSV__ENCODING = utf-8
    CSV__FIELD_NAMES_AFTER_HEADER = no
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    CSV__GROUP_BY_DATASET = no
    CSV__IN_FIELD_NAMES = YES
    CSV__IN_SEPARATOR = ,
    CSV__SCHEMA = char,12,,char,6,,char,17,
    CSV__SCHEMA_WITH_COL_NAMES = name,char,12,,RecordName,char,6,,coltype,char,17,
    CSV__SKIP_FOOTER = 0
    CSV__SKIP_LINES = 1
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__STRIP_QUOTES = yes
    DATASET = @Value(_CSV_file_name)
    FEATURETYPES_RADIO = FEATURETYPES
    FORMAT = CSV
    OUTPUT_FEATURES_DISPLAY = Based on Connections
    <OTHER> -> BulkAttributeRenamer
BulkAttributeRenamer
    ATTRCHOICE = All Attributes
    CASE_CHANGE_TYPE = lower
    MODE_CHOICE = RENAME
    PATTERN_ACTION_DISP = CASECHANGE
    -> AttributeRemover
Note: Remove some stuff we don't want going into the JSON attribute
AttributeRemover
    LIST_ATTRS = attribute{}
    REMOVE_ATTRS = _csv_file_name,fme_basename
    -> AttributeJSONPacker_2
Note: Pack all the non-ID attributes into a single JSON attribute. This custom transformer was downloaded from FME store and then modified to allow specification of attributes or wildcards to skip, as well as to include
AttributeJSONPacker_2
    FILTEREXC = idx
    PACKED = data
    SKIPATTRS = squestid,table_name,hhid,caseid,ixh4,recordname,_list_index,surveyid,_is_json,_qual_tbl_name
    -> AttributeExposer
AttributeExposer
    ATTR_LIST = data
    -> REC91 (writer POSTGRES_2)
Note: Load to tables that have been (manually) precreated to / include the correct index columns for this table plus a single jsonb data column. These tables have been added as a workspace resource so the dynamic writer knows the ID columns to write.
REC91 (writer POSTGRES_2)
    attributes: surveyid varchar(3), data text

FME custom transformer AttributeJSONPacker
This transformer packs all the attributes that are chosen, or fit the user filter, into a single attribute, as a dictionary in a JSON compatible format:
{"PRI":"2","COMMENTS":"Test Data"}
This is useful for storing multiple format attributes in a single database field for future conversions back to the original format. 
Binary attributes will be hex-encoded and prefaced with "0x". 
Packed attributes can be unpacked using the AttributeJSONUnpacker transformer.
Input Ports
    Input
Accepts any feature.
    Output Ports
    Output
Ouputs the original feature with an added attribute containing the JSON object.
    Parameters
    Attributes to Pack
    Specific attributes to pack. Chosing any attributes will disable the filter (described below).
    Filter Prefix
All attributes with this prefix will be added to the packed attribute. Leaving this value blank will pack all the attributes.
    Packed Attribute Name
The name of the new attribute containing the packed values

Parameters:
- FILTER =   # Filter Prefix to INCLUDE (blank for all attributes)
- PACKED = _packed   # Packed Attribute Name
- ATTRS =   # " " Attributes to Pack
- SKIPATTRS =   # " " Attributes to Skip Packing
- FILTEREXC =   # Filter to EXCLUDE attributes (blank to not use)

Input (input)
    -> ParameterFetcher
Note: Get filter value
ParameterFetcher
    ATTR_LIST = AttributeJSONPacker_FILTER {$(FILTER)} AttributeJSONPacker_PACKED {$(PACKED)} AttributeJSONPacker_ATTRS {$(ATTRS)} AttributeJSONPacker_SKIPATTRS {$(SKIPATTRS)} AttributeJSONPacker_FILTEREXC {$(FILTEREXC)}
    -> PythonCaller
PythonCaller
    NEW_ATTRIBUTES = $(PACKED)
    PYTHONSOURCE:
      import fmeobjects
      import binascii
      import json

      # This class will create a packed list of format
      # attributes suitable for use with @SupplyAttributes()

      def packIgdsAtts(feature):

         # get a list of attribute names
         attlist = feature.getAllAttributeNames()
         attlist = map(unicode, attlist)

         # get attributes to pack
         pack_attrs = feature.getAttribute('AttributeJSONPacker_ATTRS').replace('"', '').strip().split(',')

         skip_attrs = feature.getAttribute('AttributeJSONPacker_SKIPATTRS').replace('"', '').strip().split(',')

         # get filter value
         filter = feature.getAttribute('AttributeJSONPacker_FILTER')
         filterExc = feature.getAttribute('AttributeJSONPacker_FILTEREXC')

         # get packed attribute name
         packedAtt = feature.getAttribute('AttributeJSONPacker_PACKED')

         # disable filter if packed attribute chosen
         if pack_attrs[0] != "":
             filter = '########################################################################'

         # create list for packed attributes
         packed = {}

         # loop through attribute names
         for att in attlist:
             if ((filter in att or att in pack_attrs) and (not att in skip_attrs) and
                  (not filterExc in att) and
                  att != 'AttributeJSONPacker_ATTRS' and
                  att != 'AttributeJSONPacker_FILTER' and
                  att != 'AttributeJSONPacker_PACKED' and
                  att != 'AttributeJSONPacker_SKIPATTRS' and
                  att != 'AttributeJSONPacker_FILTEREXC' and
                  not att.startswith('fme') and
                  not att.startswith('csv')):
                 att_value = feature.getAttribute(att)
                 # convert binary attributes to hex for storage
                 if type(att_value) == bytearray:
                     att_value = "0x" + binascii.hexlify(att_value)
                 # append attribute value
                 packed[att] = att_value

         #add packed attributes in JSON format
         feature.setAttribute(packedAtt,json.dumps(packed,separators=(',', ':'), ensure_ascii=False))
    PYTHONSYMBOL = packIgdsAtts
    -> Output (output)
Output (output)
