FME workspace translate_all_recordtypes_to_pg_singly.fmw

Parameters:
- DestDataset_POSTGRES = postgres@localhost:5432/DHS_Surveys   # Connection
- SourceDataset_CSV = C:\Users\zool1301\Documents\DHS\Phase6\ExtractedSurveyRecords_Python\*.All.csv   # Source CSV (CommaSeparatedValue) File(s)
- FEATURE_TYPES =
- SourceDataset_CSV_5 = C:\Users\zool1301\Documents\DHS\Phase6\ExtractedSurveyRecords_Python\*.All.csv   # Source CSV (CommaSeparatedValue) File(s)
- SourceDataset_CSV_4 = C:\Users\zool1301\Documents\DHS\Phase6\ExtractedSurveyRecords_Python\*_All.csv   # Source CSV (CommaSeparatedValue) File(s)

Readers:
- CSV_1: CSV from $(SourceDataset_CSV)
- CSV_2: CSV from $(SourceDataset_CSV_5)
- CSV_3: CSV from $(SourceDataset_CSV_4)

Writers:
- POSTGRES_1: POSTGRES to $(DestDataset_POSTGRES)

RECHMC_All (reader CSV_3)
    attributes: FileCode char(7), HHID number(6,0), IDXHML number(2,0), SH123A number(2,0), SH123B number(3,0), SH123C number(2,0), SH123D number(2,0), SH125A number(2,0), SH127A number(2,0), SH127B number(5,0), SH128 number(3,0), SH128A number(2,0), SH128B number(5,0)
    -> FeatureTypeFilter
    -> BulkAttributeRenamer_2
BulkAttributeRenamer_2
    PATTERN_ACTION_DISP = Change Case
    ATTRCHOICE = All Attributes
    CASE_CHANGE_TYPE = lowercase
    -> RECHMC_All (writer POSTGRES_1)
RECHMC_All (writer POSTGRES_1)
    attributes: filecode char(7),PRIKEY, hhid numeric(6,0),PRIKEY, idxhml numeric(2,0),PRIKEY, sh123a numeric(2,0), sh123b numeric(3,0), sh123c numeric(2,0), sh123d numeric(2,0), sh125a numeric(2,0), sh127a numeric(2,0), sh127b numeric(5,0), sh128 numeric(3,0), sh128a numeric(2,0), sh128b numeric(5,0)
RECHML_All (reader CSV_3)
    attributes: FileCode char(7), HHID char(6), HMLIDX number(2,0), HML3 number(2,0), HML4 number(3,0), HML5 number(2,0), HML6 number(2,0), HML7 number(3,0), HML8 number(2,0), HML9 number(3,0), HML10 number(2,0), HML11 number(2,0), HML21 number(2,0), HMLA number(3,0), HMLB number(3,0), HMLC number(3,0), HMLD number(3,0), HMLE char(1)
    -> FeatureTypeFilter
    -> BulkAttributeRenamer_3
FeatureTypeFilter
BulkAttributeRenamer_3
    PATTERN_ACTION_DISP = Change Case
    ATTRCHOICE = All Attributes
    CASE_CHANGE_TYPE = lowercase
    -> RECHML_All (writer POSTGRES_1)
RECHML_All (writer POSTGRES_1)
    attributes: filecode char(7),PRIKEY, hhid char(6),PRIKEY, hmlidx numeric(2,0),PRIKEY, hml3 numeric(2,0), hml4 numeric(3,0), hml5 numeric(2,0), hml6 numeric(2,0), hml7 numeric(3,0), hml8 numeric(2,0), hml9 numeric(3,0), hml10 numeric(2,0), hml11 numeric(2,0), hml21 numeric(2,0), hmla numeric(3,0), hmlb numeric(3,0), hmlc numeric(3,0), hmld numeric(3,0), hmle char(1)
RECH4A_All (reader CSV_3)
    attributes: FileCode char(7), HHID char(7), IDXH4A number(3,0), SH6XA number(2,0), SH6XB number(2,0), SH6XC number(2,0), SH6XX number(2,0), SH6XY number(2,0), SH6XZ number(2,0), SH62A number(2,0), SH62B number(6,0), SH63 number(2,0), SH63B number(2,0), SH68A number(2,0), SH68B number(3,0), SH68C number(3,0), SH6YA number(2,0), SH6YB number(2,0), SH6YC number(2,0), SH6YD number(2,0), SH6YE number(2,0), SH6YF number(2,0), SH6YG number(2,0), SH6YH number(2,0), SH6YI number(2,0), SH6YJ number(2,0), SH6YX number(2,0), SH6YZ number(2,0), SH69A number(2,0), SH70 number(6,0),
      SH71 number(3,0), SH72 number(6,0), SH73 number(6,0), SH74 number(6,0), SH75 number(2,0), SH76 number(6,0), SH77A number(6,0), SH77B number(6,0), SH77C number(6,0), SH78 number(2,0), SH78A number(6,0), SH90 number(2,0), SH91 number(2,0), SH92 number(3,0), SH93 number(4,0), SH94 number(6,0), SH94A number(2,0), SH95 number(6,0), SH96A number(6,0), SH96B number(6,0), SH96C number(6,0)
    -> BulkAttributeRenamer_4
BulkAttributeRenamer_4
    PATTERN_ACTION_DISP = Change Case
    ATTRCHOICE = All Attributes
    CASE_CHANGE_TYPE = lowercase
    -> RECH4A_All (writer POSTGRES_1)
RECH4A_All (writer POSTGRES_1)
    attributes: filecode char(7),PRIKEY, hhid char(7),PRIKEY, idxh4a numeric(3,0),PRIKEY, sh6xa numeric(2,0), sh6xb numeric(2,0), sh6xc numeric(2,0), sh6xx numeric(2,0), sh6xy numeric(2,0), sh6xz numeric(2,0), sh62a numeric(2,0), sh62b numeric(6,0), sh63 numeric(2,0), sh63b numeric(2,0), sh68a numeric(2,0), sh68b numeric(3,0), sh68c numeric(3,0), sh6ya numeric(2,0), sh6yb numeric(2,0), sh6yc numeric(2,0), sh6yd numeric(2,0), sh6ye numeric(2,0), sh6yf numeric(2,0), sh6yg numeric(2,0), sh6yh numeric(2,0), sh6yi numeric(2,0), sh6yj numeric(2,0), sh6yx numeric(2,0), sh6yz numeric(2,0), sh69a numeric(2,0), sh70 numeric(6,0),
      sh71 numeric(3,0), sh72 numeric(6,0), sh73 numeric(6,0), sh74 numeric(6,0), sh75 numeric(2,0), sh76 numeric(6,0), sh77a numeric(6,0), sh77b numeric(6,0), sh77c numeric(6,0), sh78 numeric(2,0), sh78a numeric(6,0), sh90 numeric(2,0), sh91 numeric(2,0), sh92 numeric(3,0), sh93 numeric(4,0), sh94 numeric(6,0), sh94a numeric(2,0), sh95 numeric(6,0), sh96a numeric(6,0), sh96b numeric(6,0), sh96c numeric(6,0)
REC61_All (reader CSV_3)
    attributes: FileCode char(7), CASEID char(10), V602 number(2,0), V603 number(4,0), V604 number(2,0), V605 number(2,0), V613 number(3,0), V614 number(2,0), V616 number(4,0), V621 number(2,0), V623 number(2,0), V624 number(3,0), V625 number(2,0), V626 number(3,0), V625A number(2,0), V626A number(3,0), V627 number(3,0), V628 number(3,0), V629 number(3,0), V631 char(1), V632 number(2,0), V633A char(1), V633B char(1), V633C char(1), V633D char(1), V633E char(1), V633F char(1), V633G char(1), V634 char(1)
    -> BulkAttributeRenamer_5
BulkAttributeRenamer_5
    PATTERN_ACTION_DISP = Change Case
    ATTRCHOICE = All Attributes
    CASE_CHANGE_TYPE = lowercase
    -> REC61_All (writer POSTGRES_1)
REC61_All (writer POSTGRES_1)
    attributes: filecode char(7),PRIKEY, caseid char(10),PRIKEY, v602 numeric(2,0), v603 numeric(4,0), v604 numeric(2,0), v605 numeric(2,0), v613 numeric(3,0), v614 numeric(2,0), v616 numeric(4,0), v621 numeric(2,0), v623 numeric(2,0), v624 numeric(3,0), v625 numeric(2,0), v626 numeric(3,0), v625a numeric(2,0), v626a numeric(3,0), v627 numeric(3,0), v628 numeric(3,0), v629 numeric(3,0), v631 char(1), v632 numeric(2,0), v633a char(1), v633b char(1), v633c char(1), v633d char(1), v633e char(1), v633f char(1), v633g char(1), v634 char(1)
RECHSK_All (reader CSV_3)
    attributes: FileCode char(7), HHID char(7), HSKIDX number(3,0), HS100 number(2,0), HS101 number(2,0), HS102 number(2,0), HS103 number(2,0), HS104 number(2,0), HS105 number(2,0), HS106 number(2,0), HS107 number(2,0), HS108 number(2,0), HS109 number(2,0), HS110 number(2,0), HS111 number(2,0)
    -> BulkAttributeRenamer_6
BulkAttributeRenamer_6
    PATTERN_ACTION_DISP = Change Case
    ATTRCHOICE = All Attributes
    CASE_CHANGE_TYPE = lowercase
    -> RECHSK_All (writer POSTGRES_1)
RECHSK_All (writer POSTGRES_1)
    attributes: filecode char(7),PRIKEY, hhid char(7),PRIKEY, hskidx numeric(3,0),PRIKEY, hs100 numeric(2,0), hs101 numeric(2,0), hs102 numeric(2,0), hs103 numeric(2,0), hs104 numeric(2,0), hs105 numeric(2,0), hs106 numeric(2,0), hs107 numeric(2,0), hs108 numeric(2,0), hs109 numeric(2,0), hs110 numeric(2,0), hs111 numeric(2,0)
RECH3_All (reader CSV_3)
    attributes: FileCode char(7), HHID char(7), SHDISTRICT number(3,0), SHUPAZILA number(3,0), SHADULT35 number(2,0), SHHTEC number(4,0), SH104A number(2,0), SH104B number(3,0), SH110G number(2,0), SH110H number(2,0), SH110I number(2,0), SH110J number(2,0), SH110K number(2,0), SH110L number(2,0), SH118A number(2,0), SH118B number(2,0), SH122A number(2,0), SH122C number(5,2)
    -> BulkAttributeRenamer_7
BulkAttributeRenamer_7
    PATTERN_ACTION_DISP = Change Case
    ATTRCHOICE = All Attributes
    CASE_CHANGE_TYPE = lowercase
    -> RECH3_All (writer POSTGRES_1)
RECH3_All (writer POSTGRES_1)
    attributes: filecode char(7),PRIKEY, hhid char(7),PRIKEY, shdistrict numeric(3,0), shupazila numeric(3,0), shadult35 numeric(2,0), shhtec numeric(4,0), sh104a numeric(2,0), sh104b numeric(3,0), sh110g numeric(2,0), sh110h numeric(2,0), sh110i numeric(2,0), sh110j numeric(2,0), sh110k numeric(2,0), sh110l numeric(2,0), sh118a numeric(2,0), sh118b numeric(2,0), sh122a numeric(2,0), sh122c numeric(5,2)
RECHOV_All (reader CSV_3)
    attributes: FileCode char(7), HHID char(7), HOVIDX number(3,0), HO100 number(3,0), HO101 number(2,0), HO102 number(2,0), HO103 number(2,0), HO104 number(2,0), HO105 number(2,0), HO106 number(2,0), HO107 number(2,0), HO108 number(2,0)
    -> BulkAttributeRenamer_8
BulkAttributeRenamer_8
    PATTERN_ACTION_DISP = Change Case
    ATTRCHOICE = All Attributes
    CASE_CHANGE_TYPE = lowercase
    -> RECHOV_All (writer POSTGRES_1)
RECHOV_All (writer POSTGRES_1)
    attributes: filecode char(7),PRIKEY, hhid char(7),PRIKEY, hovidx numeric(3,0),PRIKEY, ho100 numeric(3,0), ho101 numeric(2,0), ho102 numeric(2,0), ho103 numeric(2,0), ho104 numeric(2,0), ho105 numeric(2,0), ho106 numeric(2,0), ho107 numeric(2,0), ho108 numeric(2,0)
RECHLB_All (reader CSV_3)
    attributes: FileCode char(7), HHID char(7), SHCOL21A number(3,0), SH21 number(3,0), SH22 number(2,0), SH23 number(3,0), SH24 number(2,0), SH25 number(2,0), SH26 number(3,0), SH27 number(2,0), SH28 number(3,0)
    -> BulkAttributeRenamer_9
BulkAttributeRenamer_9
    PATTERN_ACTION_DISP = Change Case
    ATTRCHOICE = All Attributes
    CASE_CHANGE_TYPE = lowercase
    -> RECHLB_All (writer POSTGRES_1)
RECHLB_All (writer POSTGRES_1)
    attributes: filecode char(7),PRIKEY, hhid char(7),PRIKEY, shcol21a numeric(3,0), sh21 numeric(3,0), sh22 numeric(2,0), sh23 numeric(3,0), sh24 numeric(2,0), sh25 numeric(2,0), sh26 numeric(3,0), sh27 numeric(2,0), sh28 numeric(3,0)
REC82_All (reader CSV_3)
    attributes: FileCode char(7), CASEID char(10), VCOL number(2,0), VCAL char(73)
    -> BulkAttributeRenamer_10
BulkAttributeRenamer_10
    PATTERN_ACTION_DISP = Change Case
    ATTRCHOICE = All Attributes
    CASE_CHANGE_TYPE = lowercase
    -> REC82_All (writer POSTGRES_1)
REC82_All (writer POSTGRES_1)
    attributes: filecode char(7),PRIKEY, caseid char(10),PRIKEY, vcol numeric(2,0), vcal char(73)
REC44_All (reader CSV_3)
    attributes: FileCode char(7), CASEID char(10), HWIDX number(2,0), HW1 number(3,0), HW2 number(5,0), HW3 number(5,0), HW4 number(5,0), HW5 number(5,0), HW6 number(6,0), HW7 number(5,0), HW8 number(5,0), HW9 number(6,0), HW10 number(5,0), HW11 number(5,0), HW12 number(6,0), HW13 number(2,0), HW15 number(2,0), HW16 number(3,0), HW17 number(3,0), HW18 number(3,0), HW19 number(5,0), HW51 number(3,0), HW52 number(2,0), HW53 number(4,0), HW55 number(2,0), HW56 number(5,0), HW57 number(2,0), HW58 char(1), HW70 number(5,0), HW71 number(5,0),
      HW72 number(5,0), HW73 number(5,0)
    -> BulkAttributeRenamer_11
BulkAttributeRenamer_11
    PATTERN_ACTION_DISP = Change Case
    ATTRCHOICE = All Attributes
    CASE_CHANGE_TYPE = lowercase
    -> REC44_All (writer POSTGRES_1)
REC44_All (writer POSTGRES_1)
    attributes: filecode char(7),PRIKEY, caseid char(10),PRIKEY, hwidx numeric(2,0),PRIKEY, hw1 numeric(3,0), hw2 numeric(5,0), hw3 numeric(5,0), hw4 numeric(5,0), hw5 numeric(5,0), hw6 numeric(6,0), hw7 numeric(5,0), hw8 numeric(5,0), hw9 numeric(6,0), hw10 numeric(5,0), hw11 numeric(5,0), hw12 numeric(6,0), hw13 numeric(2,0), hw15 numeric(2,0), hw16 numeric(3,0), hw17 numeric(3,0), hw18 numeric(3,0), hw19 numeric(5,0), hw51 numeric(3,0), hw52 numeric(2,0), hw53 numeric(4,0), hw55 numeric(2,0), hw56 numeric(5,0), hw57 numeric(2,0), hw58 char(1), hw70 numeric(5,0), hw71 numeric(5,0),
      hw72 numeric(5,0), hw73 numeric(5,0)
RECHW_All (reader CSV_3)
    attributes: FileCode char(7), HHID char(7), SHCOLD number(2,0), SH215 number(3,0), SH216 number(6,0), SH217 number(5,0), SH240 number(4,0)
    -> BulkAttributeRenamer_12
BulkAttributeRenamer_12
    PATTERN_ACTION_DISP = Change Case
    ATTRCHOICE = All Attributes
    CASE_CHANGE_TYPE = lowercase
    -> RECHW_All (writer POSTGRES_1)
RECHW_All (writer POSTGRES_1)
    attributes: filecode char(7),PRIKEY, hhid char(7),PRIKEY, shcold numeric(2,0),PRIKEY, sh215 numeric(3,0), sh216 numeric(6,0), sh217 numeric(5,0), sh240 numeric(4,0)
RECHMG_All (reader CSV_3)
    attributes: FileCode char(7), HHID char(9), SH_MIG char(15), SH22 number(2,0), SH24 number(2,0), SH25M number(3,0), SH25Y number(5,0), SH26 number(3,0), SH27 number(2,0), SH28C number(2,0), SH28D number(3,0)
    -> BulkAttributeRenamer_13
BulkAttributeRenamer_13
    PATTERN_ACTION_DISP = Change Case
    ATTRCHOICE = All Attributes
    CASE_CHANGE_TYPE = lowercase
    -> RECHMG_All (writer POSTGRES_1)
RECHMG_All (writer POSTGRES_1)
    attributes: filecode char(7),PRIKEY, hhid char(9),PRIKEY, sh_mig char(15), sh22 numeric(2,0), sh24 numeric(2,0), sh25m numeric(3,0), sh25y numeric(5,0), sh26 numeric(3,0), sh27 numeric(2,0), sh28c numeric(2,0), sh28d numeric(3,0)
REC97_All (reader CSV_3)
    attributes: FileCode char(7), CASEID char(12), S902 number(2,0), S903A number(2,0), S903B number(2,0), S903C number(2,0), S903D number(2,0), S903E number(2,0), S903F number(2,0), S903G number(2,0), S903H number(2,0), S903X number(2,0), S903Z number(2,0), S904 number(2,0), S905M number(3,0), S905Y number(5,0), S906 number(2,0), S907 number(2,0), S908 number(3,0), S909 number(2,0), S910 number(2,0), S911 number(2,0), S912 number(2,0), S913 number(3,0), S914 number(2,0), S915 number(3,0), S916 number(2,0), S917 number(3,0), S918 number(2,0), S919 number(3,0),
      S920 number(2,0), S921 number(2,0), S922 number(2,0), S923 number(2,0), S924 number(3,0), S926 number(2,0), S927 number(2,0), S928 number(2,0), S929 number(2,0), S930 number(3,0), S931 number(2,0), S932 number(2,0), S933 number(2,0), S934 number(2,0), S936 number(2,0), S937A number(2,0), S937B number(2,0), S937C number(2,0), S937D number(2,0), S937E number(2,0), S937F number(2,0), S937G number(2,0), S937H number(2,0), S937X number(2,0), S937Z number(2,0), S938 number(2,0), S939 number(2,0), S940M number(3,0), S940Y number(5,0), S941 number(2,0),
      S942 number(3,0), S943 number(2,0), S944 number(2,0), S945 number(2,0), S946 number(2,0), S947 number(2,0), S948 number(3,0), S949 number(2,0), S950 number(3,0), S951 number(3,0)
    -> BulkAttributeRenamer_14
BulkAttributeRenamer_14
    PATTERN_ACTION_DISP = Change Case
    ATTRCHOICE = All Attributes
    CASE_CHANGE_TYPE = lowercase
    -> REC97_All (writer POSTGRES_1)
REC97_All (writer POSTGRES_1)
    attributes: filecode char(7),PRIKEY, caseid char(12),PRIKEY, s902 numeric(2,0), s903a numeric(2,0), s903b numeric(2,0), s903c numeric(2,0), s903d numeric(2,0), s903e numeric(2,0), s903f numeric(2,0), s903g numeric(2,0), s903h numeric(2,0), s903x numeric(2,0), s903z numeric(2,0), s904 numeric(2,0), s905m numeric(3,0), s905y numeric(5,0), s906 numeric(2,0), s907 numeric(2,0), s908 numeric(3,0), s909 numeric(2,0), s910 numeric(2,0), s911 numeric(2,0), s912 numeric(2,0), s913 numeric(3,0), s914 numeric(2,0), s915 numeric(3,0), s916 numeric(2,0), s917 numeric(3,0), s918 numeric(2,0), s919 numeric(3,0),
      s920 numeric(2,0), s921 numeric(2,0), s922 numeric(2,0), s923 numeric(2,0), s924 numeric(3,0), s926 numeric(2,0), s927 numeric(2,0), s928 numeric(2,0), s929 numeric(2,0), s930 numeric(3,0), s931 numeric(2,0), s932 numeric(2,0), s933 numeric(2,0), s934 numeric(2,0), s936 numeric(2,0), s937a numeric(2,0), s937b numeric(2,0), s937c numeric(2,0), s937d numeric(2,0), s937e numeric(2,0), s937f numeric(2,0), s937g numeric(2,0), s937h numeric(2,0), s937x numeric(2,0), s937z numeric(2,0), s938 numeric(2,0), s939 numeric(2,0), s940m numeric(3,0), s940y numeric(5,0), s941 numeric(2,0),
      s942 numeric(3,0), s943 numeric(2,0), s944 numeric(2,0), s945 numeric(2,0), s946 numeric(2,0), s947 numeric(2,0), s948 numeric(3,0), s949 numeric(2,0), s950 numeric(3,0), s951 numeric(3,0)
RECH11_All (reader CSV_3)
    attributes: FileCode char(7), HHID number(10,0), SLNPM number(2,0), SHP216 number(3,0), SHP218 number(3,0), SHP220 number(4,0), SHP220B number(4,0), SHP221 number(4,0), SHP221B number(4,0), SHP221AH number(3,0), SHP221AM number(3,0), SHP222 number(2,0)
    -> BulkAttributeRenamer_15
BulkAttributeRenamer_15
    PATTERN_ACTION_DISP = Change Case
    ATTRCHOICE = All Attributes
    CASE_CHANGE_TYPE = lowercase
    -> RECH11_All (writer POSTGRES_1)
RECH11_All (writer POSTGRES_1)
    attributes: filecode char(7),PRIKEY, hhid numeric(10,0),PRIKEY, slnpm numeric(2,0), shp216 numeric(3,0), shp218 numeric(3,0), shp220 numeric(4,0), shp220b numeric(4,0), shp221 numeric(4,0), shp221b numeric(4,0), shp221ah numeric(3,0), shp221am numeric(3,0), shp222 numeric(2,0)
RECG2_All (reader CSV_3)
    attributes: FileCode char(7), CASEID char(9), GIDX number(2,0), G121 number(2,0), G122 number(3,0), G123 number(2,0), G124 number(3,0)
    -> BulkAttributeRenamer_16
BulkAttributeRenamer_16
    PATTERN_ACTION_DISP = Change Case
    ATTRCHOICE = All Attributes
    CASE_CHANGE_TYPE = lowercase
    -> RECG2_All (writer POSTGRES_1)
RECG2_All (writer POSTGRES_1)
    attributes: filecode char(7),PRIKEY, caseid char(9),PRIKEY, gidx numeric(2,0),PRIKEY, g121 numeric(2,0), g122 numeric(3,0), g123 numeric(2,0), g124 numeric(3,0)
RECH5S_All (reader CSV_3)
    attributes: FileCode char(7), HHID char(7), SHC0 number(3,0), SH505 number(4,0), SH506 number(5,0), SH515 number(2,0), SH516 char(6), SH517 number(2,0)
    -> BulkAttributeRenamer_17
BulkAttributeRenamer_17
    PATTERN_ACTION_DISP = Change Case
    ATTRCHOICE = All Attributes
    CASE_CHANGE_TYPE = lowercase
    -> RECH5S_All (writer POSTGRES_1)
RECH5S_All (writer POSTGRES_1)
    attributes: filecode char(7),PRIKEY, hhid char(7),PRIKEY, shc0 numeric(3,0), sh505 numeric(4,0), sh506 numeric(5,0), sh515 numeric(2,0), sh516 char(6), sh517 numeric(2,0)
RECHG1_All (reader CSV_3)
    attributes: FileCode char(7), HHID char(7), SGCONGL number(5,0), SGHOGAR number(3,0), SGESTR char(1), SGPROVIN number(3,0), SGMUNIC char(1), SGZONA number(2,0), SGRESP number(3,0), SGINT number(9,0), SGINTD number(3,0), SGINTM number(3,0), SGINTA number(5,0), SGINTNUM number(4,0), SGRESULT number(3,0), SGVISITS number(2,0), SGSUPERV number(4,0), SGEDITC number(4,0), SGEDITO number(2,0), SGDIGIT number(3,0), SGHORAI number(3,0), SGMINUTI number(3,0), SGHORAF number(3,0), SGMINUTF number(3,0), SGWEIGHT number(9,0), SINGRTH number(9,0), SINGRTHP number(9,0), SINGRHI number(2,0), SVIVIG1 number(2,0), SVIVIG2 number(2,0),
      SVALPRO number(6,0), SQUINTIP number(2,0), SALLINCI number(2,0)
    -> BulkAttributeRenamer_18
BulkAttributeRenamer_18
    PATTERN_ACTION_DISP = Change Case
    ATTRCHOICE = All Attributes
    CASE_CHANGE_TYPE = lowercase
    -> RECHG1_All (writer POSTGRES_1)
RECHG1_All (writer POSTGRES_1)
    attributes: filecode char(7),PRIKEY, hhid char(7),PRIKEY, sgcongl numeric(5,0), sghogar numeric(3,0), sgestr char(1), sgprovin numeric(3,0), sgmunic char(1), sgzona numeric(2,0), sgresp numeric(3,0), sgint numeric(9,0), sgintd numeric(3,0), sgintm numeric(3,0), sginta numeric(5,0), sgintnum numeric(4,0), sgresult numeric(3,0), sgvisits numeric(2,0), sgsuperv numeric(4,0), sgeditc numeric(4,0), sgedito numeric(2,0), sgdigit numeric(3,0), sghorai numeric(3,0), sgminuti numeric(3,0), sghoraf numeric(3,0), sgminutf numeric(3,0), sgweight numeric(9,0), singrth numeric(9,0), singrthp numeric(9,0), singrhi numeric(2,0), svivig1 numeric(2,0), svivig2 numeric(2,0),
      svalpro numeric(6,0), squintip numeric(2,0), sallinci numeric(2,0)
REC71_All (reader CSV_3)
    attributes: FileCode char(7), CASEID char(10), V701 number(2,0), V702 number(3,0), V704 number(3,0), V705 char(1), V714 number(2,0), V714A number(2,0), V715 number(3,0), V716 number(3,0), V717 char(1), V719 number(2,0), V721 char(1), V729 number(2,0), V730 number(3,0), V731 number(2,0), V732 number(2,0), V739 number(2,0), V740 char(1), V741 number(2,0), V743A number(2,0), V743B number(2,0), V743C char(1), V743D number(2,0), V743E char(1), V743F char(1), V744A number(2,0), V744B number(2,0), V744C number(2,0), V744D number(2,0),
      V744E number(2,0), V745A char(1), V745B char(1), V746 char(1)
    -> BulkAttributeRenamer_19
BulkAttributeRenamer_19
    PATTERN_ACTION_DISP = Change Case
    ATTRCHOICE = All Attributes
    CASE_CHANGE_TYPE = lowercase
    -> REC71_All (writer POSTGRES_1)
REC71_All (writer POSTGRES_1)
    attributes: filecode char(7),PRIKEY, caseid char(10),PRIKEY, v701 numeric(2,0), v702 numeric(3,0), v704 numeric(3,0), v705 char(1), v714 numeric(2,0), v714a numeric(2,0), v715 numeric(3,0), v716 numeric(3,0), v717 char(1), v719 numeric(2,0), v721 char(1), v729 numeric(2,0), v730 numeric(3,0), v731 numeric(2,0), v732 numeric(2,0), v739 numeric(2,0), v740 char(1), v741 numeric(2,0), v743a numeric(2,0), v743b numeric(2,0), v743c char(1), v743d numeric(2,0), v743e char(1), v743f char(1), v744a numeric(2,0), v744b numeric(2,0), v744c numeric(2,0), v744d numeric(2,0),
      v744e numeric(2,0), v745a char(1), v745b char(1), v746 char(1)
RECHMH2_All (reader CSV_3)
    attributes: FileCode char(7), HHID char(6), HMHIDX2 number(3,0), SH212D number(2,0)
    -> BulkAttributeRenamer_20
BulkAttributeRenamer_20
    PATTERN_ACTION_DISP = Change Case
    ATTRCHOICE = All Attributes
    CASE_CHANGE_TYPE = lowercase
    -> RECHMH2_All (writer POSTGRES_1)
RECHMH2_All (writer POSTGRES_1)
    attributes: filecode char(7),PRIKEY, hhid char(6),PRIKEY, hmhidx2 numeric(3,0),PRIKEY, sh212d numeric(2,0)
RECH7_All (reader CSV_3)
    attributes: FileCode char(7), HHID char(7), SH230 number(3,0), SH231 number(3,0), SH232 number(3,0), SH234 number(3,0), SH234C number(6,0), SH235 number(6,0), SH237 number(6,0), SH238 number(6,0), SH239 number(6,0), SH241 number(6,0), SH242A number(6,0), SH242B number(2,0), SH242C number(3,0), SH243 number(3,0), SH244 number(6,0), SH245 number(6,0), SH246S number(6,0), SH246D number(6,0), SH248 number(6,0), SH249 number(6,0), SH250 number(6,0), SH253 number(5,0), SH254 number(3,0), SH255S number(4,0), SH255D number(4,0), SH257 number(3,0), SH258 number(3,0), SH259 number(6,0),
      SH260 number(6,0), SH262 number(6,0), SH263 number(6,0), SH264S number(4,0), SH264D number(4,0), FSYSTO number(4,0), FDYSTO number(4,0), SH271 number(5,0), SH273 number(5,0), SH276 number(2,0), SHWH number(2,0), SH1 number(14,0), SH1D number(3,0), SH1MO number(3,0), SH1Y number(5,0), SH1H number(3,0), SH1M number(3,0), SH1X number(2,0), SH2 number(14,0), SH2D number(3,0), SH2MO number(3,0), SH2Y number(5,0), SH2H number(3,0), SH2M number(3,0), SH2X number(2,0), SH3 number(14,0), SH3D number(3,0), SH3MO number(3,0), SH3Y number(5,0), SH3H number(3,0),
      SH3M number(3,0), SH3X number(2,0), SH279 number(2,0), SH280 number(5,0), SH281 number(5,0), SH283 number(9,0), SH283D number(3,0), SH283M number(3,0), SH283Y number(5,0), SH283T number(5,0), SH284 number(4,0), SH284A number(4,0), SH284G number(4,0), SH284B number(4,0), SHPC1 number(5,0), SHSD1 number(5,0), SHRM1 number(6,0), SHRM3 number(6,0), SHRM4 number(6,0), SHRM5 number(6,0), SHSD3 number(5,0), SHBM number(5,0), SHRI number(5,0), SHCMC number(4,0), SHFLG number(2,0), SHSMK char(1), SHRESI number(2,0), SHED1 number(2,0), SHED2 number(3,0), SHED3 number(2,0)
    -> BulkAttributeRenamer_21
BulkAttributeRenamer_21
    PATTERN_ACTION_DISP = Change Case
    ATTRCHOICE = All Attributes
    CASE_CHANGE_TYPE = lowercase
    -> RECH7_All (writer POSTGRES_1)
RECH7_All (writer POSTGRES_1)
    attributes: filecode char(7),PRIKEY, hhid char(7),PRIKEY, sh230 numeric(3,0), sh231 numeric(3,0), sh232 numeric(3,0), sh234 numeric(3,0), sh234c numeric(6,0), sh235 numeric(6,0), sh237 numeric(6,0), sh238 numeric(6,0), sh239 numeric(6,0), sh241 numeric(6,0), sh242a numeric(6,0), sh242b numeric(2,0), sh242c numeric(3,0), sh243 numeric(3,0), sh244 numeric(6,0), sh245 numeric(6,0), sh246s numeric(6,0), sh246d numeric(6,0), sh248 numeric(6,0), sh249 numeric(6,0), sh250 numeric(6,0), sh253 numeric(5,0), sh254 numeric(3,0), sh255s numeric(4,0), sh255d numeric(4,0), sh257 numeric(3,0), sh258 numeric(3,0), sh259 numeric(6,0),
      sh260 numeric(6,0), sh262 numeric(6,0), sh263 numeric(6,0), sh264s numeric(4,0), sh264d numeric(4,0), fsysto numeric(4,0), fdysto numeric(4,0), sh271 numeric(5,0), sh273 numeric(5,0), sh276 numeric(2,0), shwh numeric(2,0), sh1 numeric(14,0), sh1d numeric(3,0), sh1mo numeric(3,0), sh1y numeric(5,0), sh1h numeric(3,0), sh1m numeric(3,0), sh1x numeric(2,0), sh2 numeric(14,0), sh2d numeric(3,0), sh2mo numeric(3,0), sh2y numeric(5,0), sh2h numeric(3,0), sh2m numeric(3,0), sh2x numeric(2,0), sh3 numeric(14,0), sh3d numeric(3,0), sh3mo numeric(3,0), sh3y numeric(5,0), sh3h numeric(3,0),
      sh3m numeric(3,0), sh3x numeric(2,0), sh279 numeric(2,0), sh280 numeric(5,0), sh281 numeric(5,0), sh283 numeric(9,0), sh283d numeric(3,0), sh283m numeric(3,0), sh283y numeric(5,0), sh283t numeric(5,0), sh284 numeric(4,0), sh284a numeric(4,0), sh284g numeric(4,0), sh284b numeric(4,0), shpc1 numeric(5,0), shsd1 numeric(5,0), shrm1 numeric(6,0), shrm3 numeric(6,0), shrm4 numeric(6,0), shrm5 numeric(6,0), shsd3 numeric(5,0), shbm numeric(5,0), shri numeric(5,0), shcmc numeric(4,0), shflg numeric(2,0), shsmk char(1), shresi numeric(2,0), shed1 numeric(2,0), shed2 numeric(3,0), shed3 numeric(2,0)
RECHMCS_All (reader CSV_3)
    attributes: FileCode char(7), HHID char(7), IDXMCS number(3,0), SH268 number(2,0), SH268I number(4,0), SH278 number(2,0), SH279 number(2,0), SH279A number(2,0), SH286 number(2,0), SH286I number(4,0), SH292 number(2,0), SH295BC char(6), SH295 number(2,0), SH295A number(9,0), SH295AD number(3,0), SH295AM number(3,0), SH295AY number(5,0), SH295B number(5,0), SH295BH number(3,0), SH295BM number(3,0)
    -> BulkAttributeRenamer_22
BulkAttributeRenamer_22
    PATTERN_ACTION_DISP = Change Case
    ATTRCHOICE = All Attributes
    CASE_CHANGE_TYPE = lowercase
    -> RECHMCS_All (writer POSTGRES_1)
RECHMCS_All (writer POSTGRES_1)
    attributes: filecode char(7),PRIKEY, hhid char(7),PRIKEY, idxmcs numeric(3,0),PRIKEY, sh268 numeric(2,0), sh268i numeric(4,0), sh278 numeric(2,0), sh279 numeric(2,0), sh279a numeric(2,0), sh286 numeric(2,0), sh286i numeric(4,0), sh292 numeric(2,0), sh295bc char(6), sh295 numeric(2,0), sh295a numeric(9,0), sh295ad numeric(3,0), sh295am numeric(3,0), sh295ay numeric(5,0), sh295b numeric(5,0), sh295bh numeric(3,0), sh295bm numeric(3,0)
RECHI_All (reader CSV_3)
    attributes: FileCode char(7), HHID char(7), SHCOLB number(2,0), SH61 number(3,0), SH62 number(2,0), SH63 number(3,0)
    -> BulkAttributeRenamer_23
BulkAttributeRenamer_23
    PATTERN_ACTION_DISP = Change Case
    ATTRCHOICE = All Attributes
    CASE_CHANGE_TYPE = lowercase
    -> RECHI_All (writer POSTGRES_1)
RECHI_All (writer POSTGRES_1)
    attributes: filecode char(7),PRIKEY, hhid char(7),PRIKEY, shcolb numeric(2,0), sh61 numeric(3,0), sh62 numeric(2,0), sh63 numeric(3,0)
REC01_All (reader CSV_3)
    attributes: FileCode char(7), CASEID char(18), V000 char(4), V001 number(4,0), V002 number(4,0), V003 number(3,0), V004 number(4,0), V005 number(8,0), V006 number(3,0), V007 number(5,0), V008 number(5,0), V009 number(3,0), V010 number(5,0), V011 number(5,0), V012 number(3,0), V013 number(2,0), V014 number(2,0), V015 number(2,0), V016 number(3,0), V017 number(5,0), V018 number(3,0), V019 number(3,0), V019A number(2,0), V020 number(2,0), V021 number(4,0), V022 number(3,0), V023 number(3,0), V024 number(2,0), V025 number(2,0), V026 number(2,0),
      V027 number(2,0), V028 number(4,0), V029 number(2,0), V030 number(3,0), V031 number(4,0), V032 number(2,0), V034 number(3,0), V040 number(4,0), V042 number(2,0), V044 char(1)
    -> REC01_All (writer POSTGRES_1)
REC01_All (writer POSTGRES_1)
    attributes: filecode char(7),PRIKEY, caseid char(18),PRIKEY, v000 char(4), v001 numeric(4,0), v002 numeric(4,0), v003 numeric(3,0), v004 numeric(4,0), v005 numeric(8,0), v006 numeric(3,0), v007 numeric(5,0), v008 numeric(5,0), v009 numeric(3,0), v010 numeric(5,0), v011 numeric(5,0), v012 numeric(3,0), v013 numeric(2,0), v014 numeric(2,0), v015 numeric(2,0), v016 numeric(3,0), v017 numeric(5,0), v018 numeric(3,0), v019 numeric(3,0), v019a numeric(2,0), v020 numeric(2,0), v021 numeric(4,0), v022 numeric(3,0), v023 numeric(3,0), v024 numeric(2,0), v025 numeric(2,0), v026 numeric(2,0),
      v027 numeric(2,0), v028 numeric(4,0), v029 numeric(2,0), v030 numeric(3,0), v031 numeric(4,0), v032 numeric(2,0), v034 numeric(3,0), v040 numeric(4,0), v042 numeric(2,0), v044 char(1)
RECML_All (reader CSV_3)
    attributes: FileCode char(7), CASEID char(9), IDXML number(2,0), ML0 number(2,0), ML1 number(3,0), ML2 number(2,0), ML11 char(1), ML12 char(1), ML13A number(2,0), ML13B number(2,0), ML13C number(2,0), ML13D number(2,0), ML13E number(2,0), ML13F char(1), ML13G char(1), ML13H number(2,0), ML13I number(2,0), ML13J number(2,0), ML13K number(2,0), ML13L number(2,0), ML13M number(2,0), ML13N char(1), ML13O char(1), ML13P char(1), ML13X number(2,0), ML13Y number(2,0), ML13Z number(2,0), ML14A char(1), ML14B char(1), ML14Y char(1),
      ML14Z char(1), ML15A number(2,0), ML15B char(1), ML15C char(1), ML16A number(2,0), ML16B char(1), ML16C char(1), ML17A number(2,0), ML17B char(1), ML17C char(1), ML18A number(2,0), ML18B char(1), ML18C char(1), ML19A char(1), ML19B char(1), ML19C char(1), ML19D char(1), ML19E char(1), ML19F char(1), ML19X char(1), ML19Y char(1), ML19Z char(1), ML20A number(2,0), ML20B char(1), ML20C char(1), ML21A char(1), ML21B char(1), ML21C char(1), ML22A char(1), ML22B char(1),
      ML22C char(1), ML23A number(2,0), ML23B char(1), ML23C char(1), ML24C char(1)
    -> RECML_All (writer POSTGRES_1)
RECML_All (writer POSTGRES_1)
    attributes: filecode char(7),PRIKEY, caseid char(9),PRIKEY, idxml numeric(2,0),PRIKEY, ml0 numeric(2,0), ml1 numeric(3,0), ml2 numeric(2,0), ml11 char(1), ml12 char(1), ml13a numeric(2,0), ml13b numeric(2,0), ml13c numeric(2,0), ml13d numeric(2,0), ml13e numeric(2,0), ml13f char(1), ml13g char(1), ml13h numeric(2,0), ml13i numeric(2,0), ml13j numeric(2,0), ml13k numeric(2,0), ml13l numeric(2,0), ml13m numeric(2,0), ml13n char(1), ml13o char(1), ml13p char(1), ml13x numeric(2,0), ml13y numeric(2,0), ml13z numeric(2,0), ml14a char(1), ml14b char(1), ml14y char(1),
      ml14z char(1), ml15a numeric(2,0), ml15b char(1), ml15c char(1), ml16a numeric(2,0), ml16b char(1), ml16c char(1), ml17a numeric(2,0), ml17b char(1), ml17c char(1), ml18a numeric(2,0), ml18b char(1), ml18c char(1), ml19a char(1), ml19b char(1), ml19c char(1), ml19d char(1), ml19e char(1), ml19f char(1), ml19x char(1), ml19y char(1), ml19z char(1), ml20a numeric(2,0), ml20b char(1), ml20c char(1), ml21a char(1), ml21b char(1), ml21c char(1), ml22a char(1), ml22b char(1),
      ml22c char(1), ml23a numeric(2,0), ml23b char(1), ml23c char(1), ml24c char(1)
REC92_All (reader CSV_3)
    attributes: FileCode char(7), CASEID char(12), IDX92 number(3,0), S222 number(2,0)
    -> REC92_All (writer POSTGRES_1)
REC92_All (writer POSTGRES_1)
    attributes: filecode char(7), caseid char(12), idx92 numeric(3,0), s222 numeric(2,0)
RECHMT_All (reader CSV_3)
    attributes: FileCode char(7), HHID char(7), SHMTX number(2,0), SH78 number(2,0), SH79 number(3,0), SH80M number(3,0), SH80A number(5,0), SH81 number(2,0), SH80MI number(3,0), SH80AI number(5,0), SH80C number(3,0)
    -> RECHMT_All (writer POSTGRES_1)
RECHMT_All (writer POSTGRES_1)
    attributes: filecode char(7), hhid char(7), shmtx numeric(2,0), sh78 numeric(2,0), sh79 numeric(3,0), sh80m numeric(3,0), sh80a numeric(5,0), sh81 numeric(2,0), sh80mi numeric(3,0), sh80ai numeric(5,0), sh80c numeric(3,0)
RECHCH2_All (reader CSV_3)
    attributes: FileCode char(7), HHID char(6), IDXCH2 number(3,0), SCHL145 number(2,0)
    -> RECHCH2_All (writer POSTGRES_1)
RECHCH2_All (writer POSTGRES_1)
    attributes: filecode char(7), hhid char(6), idxch2 numeric(3,0), schl145 numeric(2,0)
REC22_All (reader CSV_3)
    attributes: FileCode char(7), CASEID char(10), V201 number(3,0), V202 number(2,0), V203 number(2,0), V204 number(2,0), V205 number(2,0), V206 number(3,0), V207 number(2,0), V208 number(2,0), V209 number(2,0), V210 number(2,0), V211 number(5,0), V212 number(3,0), V213 number(2,0), V214 number(2,0), V215 number(4,0), V216 number(2,0), V217 char(1), V218 number(3,0), V219 number(3,0), V220 number(2,0), V221 number(4,0), V222 number(4,0), V223 number(2,0), V224 number(3,0), V225 number(2,0), V226 number(4,0), V227 number(2,0), V228 number(2,0),
      V229 number(3,0), V230 number(5,0), V231 number(5,0), V232 number(2,0), V233 number(2,0), V234 number(2,0), V235 number(2,0), V237 number(2,0), V238 number(2,0), V239 number(2,0), V240 number(3,0), V241 number(5,0), V242 number(5,0), V243 number(2,0)
    -> REC22_All (writer POSTGRES_1)
REC22_All (writer POSTGRES_1)
    attributes: filecode char(7), caseid char(10), v201 numeric(3,0), v202 numeric(2,0), v203 numeric(2,0), v204 numeric(2,0), v205 numeric(2,0), v206 numeric(3,0), v207 numeric(2,0), v208 numeric(2,0), v209 numeric(2,0), v210 numeric(2,0), v211 numeric(5,0), v212 numeric(3,0), v213 numeric(2,0), v214 numeric(2,0), v215 numeric(4,0), v216 numeric(2,0), v217 char(1), v218 numeric(3,0), v219 numeric(3,0), v220 numeric(2,0), v221 numeric(4,0), v222 numeric(4,0), v223 numeric(2,0), v224 numeric(3,0), v225 numeric(2,0), v226 numeric(4,0), v227 numeric(2,0), v228 numeric(2,0),
      v229 numeric(3,0), v230 numeric(5,0), v231 numeric(5,0), v232 numeric(2,0), v233 numeric(2,0), v234 numeric(2,0), v235 numeric(2,0), v237 numeric(2,0), v238 numeric(2,0), v239 numeric(2,0), v240 numeric(3,0), v241 numeric(5,0), v242 numeric(5,0), v243 numeric(2,0)
REC75_All (reader CSV_3)
    attributes: FileCode char(7), CASEID char(10), V750 number(2,0), V751 number(2,0), V754BP char(1), V754CP number(2,0), V754DP number(2,0), V754JP number(2,0), V754WP number(2,0), V756 number(2,0), V761 char(1), V761B char(1), V761C char(1), V762AA char(1), V762AB char(1), V762AC char(1), V762AD char(1), V762AE char(1), V762AF char(1), V762AG char(1), V762AH char(1), V762AI char(1), V762AJ char(1), V762AK char(1), V762AL char(1), V762AM char(1), V762AN char(1), V762AO char(1), V762AP char(1), V762AQ char(1),
      V762AR char(1), V762AS char(1), V762AT char(1), V762AU char(1), V762AV char(1), V762AW char(1), V762AX char(1), V762AZ char(1), V762BA char(1), V762BB char(1), V762BC char(1), V762BD char(1), V762BE char(1), V762BF char(1), V762BG char(1), V762BH char(1), V762BI char(1), V762BJ char(1), V762BK char(1), V762BL char(1), V762BM char(1), V762BN char(1), V762BO char(1), V762BP char(1), V762BQ char(1), V762BR char(1), V762BS char(1), V762BT char(1), V762BU char(1), V762BV char(1),
      V762BW char(1), V762BX char(1), V762BZ char(1), V763A number(2,0), V763B number(2,0), V763C number(2,0), V763D char(1), V763E char(1), V763F char(1), V763G char(1), V766A char(1), V766B char(1), V767A char(1), V767B char(1), V767C char(1), V768A char(1), V768B char(1), V768C char(1), V769 char(1), V769A char(1), V770 number(2,0), V770A number(2,0), V770B number(2,0), V770C number(2,0), V770D number(2,0), V770E number(2,0), V770F number(2,0), V770G number(2,0), V770H number(2,0), V770I number(2,0),
      V770J number(2,0), V770K char(1), V770L number(2,0), V770M number(2,0), V770N number(2,0), V770O number(2,0), V770P number(2,0), V770Q number(2,0), V770R number(2,0), V770S number(2,0), V770T number(2,0), V770U number(2,0), V770V number(2,0), V770W number(2,0), V770X number(2,0), V774A number(2,0), V774B number(2,0), V774C number(2,0), V775 char(1), V777 char(1), V778 char(1), V779 char(1), V780 char(1), V781 char(1), V783 char(1), V784A char(1), V784B char(1), V784C char(1), V784D char(1), V784E char(1),
      V784F char(1), V784G char(1), V784H char(1), V784I char(1), V784J char(1), V784K char(1), V784L char(1), V784M char(1), V784N char(1), V784O char(1), V784P char(1), V784Q char(1), V784R char(1), V784S char(1), V784T char(1), V784U char(1), V784V char(1), V784X char(1), V785 number(2,0)
    -> REC75_All (writer POSTGRES_1)
REC75_All (writer POSTGRES_1)
    attributes: filecode char(7), caseid char(10), v750 numeric(2,0), v751 numeric(2,0), v754bp char(1), v754cp numeric(2,0), v754dp numeric(2,0), v754jp numeric(2,0), v754wp numeric(2,0), v756 numeric(2,0), v761 char(1), v761b char(1), v761c char(1), v762aa char(1), v762ab char(1), v762ac char(1), v762ad char(1), v762ae char(1), v762af char(1), v762ag char(1), v762ah char(1), v762ai char(1), v762aj char(1), v762ak char(1), v762al char(1), v762am char(1), v762an char(1), v762ao char(1), v762ap char(1), v762aq char(1),
      v762ar char(1), v762as char(1), v762at char(1), v762au char(1), v762av char(1), v762aw char(1), v762ax char(1), v762az char(1), v762ba char(1), v762bb char(1), v762bc char(1), v762bd char(1), v762be char(1), v762bf char(1), v762bg char(1), v762bh char(1), v762bi char(1), v762bj char(1), v762bk char(1), v762bl char(1), v762bm char(1), v762bn char(1), v762bo char(1), v762bp char(1), v762bq char(1), v762br char(1), v762bs char(1), v762bt char(1), v762bu char(1), v762bv char(1),
      v762bw char(1), v762bx char(1), v762bz char(1), v763a numeric(2,0), v763b numeric(2,0), v763c numeric(2,0), v763d char(1), v763e char(1), v763f char(1), v763g char(1), v766a char(1), v766b char(1), v767a char(1), v767b char(1), v767c char(1), v768a char(1), v768b char(1), v768c char(1), v769 char(1), v769a char(1), v770 numeric(2,0), v770a numeric(2,0), v770b numeric(2,0), v770c numeric(2,0), v770d numeric(2,0), v770e numeric(2,0), v770f numeric(2,0), v770g numeric(2,0), v770h numeric(2,0), v770i numeric(2,0),
      v770j numeric(2,0), v770k char(1), v770l numeric(2,0), v770m numeric(2,0), v770n numeric(2,0), v770o numeric(2,0), v770p numeric(2,0), v770q numeric(2,0), v770r numeric(2,0), v770s numeric(2,0), v770t numeric(2,0), v770u numeric(2,0), v770v numeric(2,0), v770w numeric(2,0), v770x numeric(2,0), v774a numeric(2,0), v774b numeric(2,0), v774c numeric(2,0), v775 char(1), v777 char(1), v778 char(1), v779 char(1), v780 char(1), v781 char(1), v783 char(1), v784a char(1), v784b char(1), v784c char(1), v784d char(1), v784e char(1),
      v784f char(1), v784g char(1), v784h char(1), v784i char(1), v784j char(1), v784k char(1), v784l char(1), v784m char(1), v784n char(1), v784o char(1), v784p char(1), v784q char(1), v784r char(1), v784s char(1), v784t char(1), v784u char(1), v784v char(1), v784x char(1), v785 numeric(2,0)
RECH2_All (reader CSV_3)
    attributes: FileCode char(7), HHID char(7), HV201 number(3,0), HV202 char(1), HV204 number(4,0), HV205 number(3,0), HV206 number(2,0), HV207 number(2,0), HV208 number(2,0), HV209 number(2,0), HV210 number(2,0), HV211 number(2,0), HV212 char(1), HV213 number(3,0), HV214 number(3,0), HV215 number(3,0), HV216 number(3,0), HV217 number(2,0), HV218 number(2,0), HV219 number(2,0), HV220 number(3,0), HV221 number(2,0), HV225 number(2,0), HV226 number(3,0), HV227 char(1), HV228 char(1), HV230A number(2,0), HV230B number(2,0), HV232 number(2,0), HV232B number(2,0),
      HV232C number(2,0), HV232D number(2,0), HV232E char(1), HV232Y number(2,0), HV234 char(1), HV234A number(2,0), HV235 number(2,0), HV236 char(1), HV237 number(2,0), HV237A number(2,0), HV237B number(2,0), HV237C number(2,0), HV237D number(2,0), HV237E number(2,0), HV237F number(2,0), HV237G number(2,0), HV237H char(1), HV237I char(1), HV237J char(1), HV237K char(1), HV237X number(2,0), HV237Z number(2,0), HV238 number(3,0), HV239 char(1), HV240 char(1), HV241 number(2,0), HV242 number(2,0), HV243A number(2,0), HV243B char(1), HV243C char(1),
      HV243D char(1), HV244 number(2,0), HV245 number(4,0), HV246 number(2,0), HV246A char(1), HV246B number(3,0), HV246C char(1), HV246D char(1), HV246E char(1), HV246F char(1), HV246G number(3,0), HV246H number(3,0), HV246I number(3,0), HV246J char(1), HV246K char(1), HV247 number(2,0), HV252 number(2,0), HV253 char(1), HV253A char(1), HV253B char(1), HV253C char(1), HV253D char(1), HV253E char(1), HV253F char(1), HV253G char(1), HV253H char(1), HV253X char(1), HV253Z char(1), HV270 number(2,0), HV271 number(8,0),
      HML1 char(1), HML1A char(1), HML2 char(1)
    -> RECH2_All (writer POSTGRES_1)
RECH2_All (writer POSTGRES_1)
    attributes: filecode char(7), hhid char(7), hv201 numeric(3,0), hv202 char(1), hv204 numeric(4,0), hv205 numeric(3,0), hv206 numeric(2,0), hv207 numeric(2,0), hv208 numeric(2,0), hv209 numeric(2,0), hv210 numeric(2,0), hv211 numeric(2,0), hv212 char(1), hv213 numeric(3,0), hv214 numeric(3,0), hv215 numeric(3,0), hv216 numeric(3,0), hv217 numeric(2,0), hv218 numeric(2,0), hv219 numeric(2,0), hv220 numeric(3,0), hv221 numeric(2,0), hv225 numeric(2,0), hv226 numeric(3,0), hv227 char(1), hv228 char(1), hv230a numeric(2,0), hv230b numeric(2,0), hv232 numeric(2,0), hv232b numeric(2,0),
      hv232c numeric(2,0), hv232d numeric(2,0), hv232e char(1), hv232y numeric(2,0), hv234 char(1), hv234a numeric(2,0), hv235 numeric(2,0), hv236 char(1), hv237 numeric(2,0), hv237a numeric(2,0), hv237b numeric(2,0), hv237c numeric(2,0), hv237d numeric(2,0), hv237e numeric(2,0), hv237f numeric(2,0), hv237g numeric(2,0), hv237h char(1), hv237i char(1), hv237j char(1), hv237k char(1), hv237x numeric(2,0), hv237z numeric(2,0), hv238 numeric(3,0), hv239 char(1), hv240 char(1), hv241 numeric(2,0), hv242 numeric(2,0), hv243a numeric(2,0), hv243b char(1), hv243c char(1),
      hv243d char(1), hv244 numeric(2,0), hv245 numeric(4,0), hv246 numeric(2,0), hv246a char(1), hv246b numeric(3,0), hv246c char(1), hv246d char(1), hv246e char(1), hv246f char(1), hv246g numeric(3,0), hv246h numeric(3,0), hv246i numeric(3,0), hv246j char(1), hv246k char(1), hv247 numeric(2,0), hv252 numeric(2,0), hv253 char(1), hv253a char(1), hv253b char(1), hv253c char(1), hv253d char(1), hv253e char(1), hv253f char(1), hv253g char(1), hv253h char(1), hv253x char(1), hv253z char(1), hv270 numeric(2,0), hv271 numeric(8,0),
      hml1 char(1), hml1a char(1), hml2 char(1)
RECH6S_All (reader CSV_3)
    attributes: FileCode char(7), HHID char(7), SHA0 number(3,0), SH603 number(6,0), SH604 number(5,0), SH614 number(2,0), SH615 char(6), SH616 number(2,0), SH617 number(2,0), SH618 char(6), SH619 number(2,0)
    -> RECH6S_All (writer POSTGRES_1)
RECH6S_All (writer POSTGRES_1)
    attributes: filecode char(7), hhid char(7), sha0 numeric(3,0), sh603 numeric(6,0), sh604 numeric(5,0), sh614 numeric(2,0), sh615 char(6), sh616 numeric(2,0), sh617 numeric(2,0), sh618 char(6), sh619 numeric(2,0)
REC81_All (reader CSV_3)
    attributes: FileCode char(7), CASEID char(10), V801 number(5,0), V802 number(5,0), V803 number(3,0), V804 number(2,0), V805 number(4,0), V806 number(2,0), V811 number(2,0), V812 number(2,0), V813 number(2,0), V814 number(2,0), V815A char(1), V815B char(1), V815C char(1)
    -> REC81_All (writer POSTGRES_1)
REC81_All (writer POSTGRES_1)
    attributes: filecode char(7), caseid char(10), v801 numeric(5,0), v802 numeric(5,0), v803 numeric(3,0), v804 numeric(2,0), v805 numeric(4,0), v806 numeric(2,0), v811 numeric(2,0), v812 numeric(2,0), v813 numeric(2,0), v814 numeric(2,0), v815a char(1), v815b char(1), v815c char(1)
REC43_All (reader CSV_3)
    attributes: FileCode char(7), CASEID char(10), HIDX number(2,0), H1 number(2,0), H2 number(2,0), H2D number(3,0), H2M number(3,0), H2Y number(5,0), H3 number(2,0), H3D number(3,0), H3M number(3,0), H3Y number(5,0), H4 number(2,0), H4D number(3,0), H4M number(3,0), H4Y number(5,0), H5 number(2,0), H5D number(3,0), H5M number(3,0), H5Y number(5,0), H6 number(2,0), H6D number(3,0), H6M number(3,0), H6Y number(5,0), H7 number(2,0), H7D number(3,0), H7M number(3,0), H7Y number(5,0), H8 number(2,0), H8D number(3,0),
      H8M number(3,0), H8Y number(5,0), H9 number(2,0), H9D number(3,0), H9M number(3,0), H9Y number(5,0), H0 number(2,0), H0D number(3,0), H0M number(3,0), H0Y number(5,0), H10 number(2,0), H11 number(2,0), H11B number(2,0), H12A number(2,0), H12B number(2,0), H12C number(2,0), H12D number(2,0), H12E number(2,0), H12F number(2,0), H12G number(2,0), H12H number(2,0), H12I number(2,0), H12J number(2,0), H12K number(2,0), H12L number(2,0), H12M number(2,0), H12N number(2,0), H12O number(2,0), H12P number(2,0), H12Q char(1),
      H12R char(1), H12S number(2,0), H12T number(2,0), H12U number(2,0), H12V number(2,0), H12W char(1), H12X number(2,0), H12Y number(2,0), H12Z number(2,0), H13 number(2,0), H13B number(2,0), H14 number(2,0), H15 number(2,0), H15A number(2,0), H15B number(2,0), H15C number(2,0), H15D number(2,0), H15E number(2,0), H15F number(2,0), H15G number(2,0), H15H number(2,0), H15I number(2,0), H15J char(1), H15K char(1), H15L char(1), H15M char(1), H20 number(2,0), H21A number(2,0), H21 number(2,0), H22 number(2,0),
      H31 number(2,0), H31B number(2,0), H31C number(2,0), H31D number(2,0), H31E number(2,0), H32A number(2,0), H32B number(2,0), H32C number(2,0), H32D number(2,0), H32E number(2,0), H32F number(2,0), H32G number(2,0), H32H number(2,0), H32I number(2,0), H32J number(2,0), H32K number(2,0), H32L number(2,0), H32M number(2,0), H32N number(2,0), H32O number(2,0), H32P number(2,0), H32Q char(1), H32R char(1), H32S number(2,0), H32T number(2,0), H32U number(2,0), H32V number(2,0), H32W number(2,0), H32X number(2,0), H32Y number(2,0),
      H32Z number(2,0), H33 number(2,0), H33D number(3,0), H33M number(3,0), H33Y number(5,0), H34 number(2,0), H35 char(1), H36A number(2,0), H36B number(2,0), H36C number(2,0), H36D number(2,0), H36E char(1), H36F char(1), H37A number(2,0), H37B number(2,0), H37C char(1), H37D number(2,0), H37E number(2,0), H37F char(1), H37G char(1), H37H number(2,0), H37I number(2,0), H37J number(2,0), H37K number(2,0), H37L number(2,0), H37M number(2,0), H37N number(2,0), H37O number(2,0), H37P number(2,0), H37X number(2,0),
      H37Y number(2,0), H37Z number(2,0), H38 number(2,0), H39 number(2,0), H40 char(1), H40D char(1), H40M char(1), H40Y char(1), H41A char(1), H41B char(1), H42 number(2,0), H43 number(2,0), H44A number(3,0), H44B char(1), H44C char(1), H45 char(1), H46A number(3,0), H46B char(1), H47 number(2,0)
    -> REC43_All (writer POSTGRES_1)
REC43_All (writer POSTGRES_1)
    attributes: filecode char(7), caseid char(10), hidx numeric(2,0), h1 numeric(2,0), h2 numeric(2,0), h2d numeric(3,0), h2m numeric(3,0), h2y numeric(5,0), h3 numeric(2,0), h3d numeric(3,0), h3m numeric(3,0), h3y numeric(5,0), h4 numeric(2,0), h4d numeric(3,0), h4m numeric(3,0), h4y numeric(5,0), h5 numeric(2,0), h5d numeric(3,0), h5m numeric(3,0), h5y numeric(5,0), h6 numeric(2,0), h6d numeric(3,0), h6m numeric(3,0), h6y numeric(5,0), h7 numeric(2,0), h7d numeric(3,0), h7m numeric(3,0), h7y numeric(5,0), h8 numeric(2,0), h8d numeric(3,0),
      h8m numeric(3,0), h8y numeric(5,0), h9 numeric(2,0), h9d numeric(3,0), h9m numeric(3,0), h9y numeric(5,0), h0 numeric(2,0), h0d numeric(3,0), h0m numeric(3,0), h0y numeric(5,0), h10 numeric(2,0), h11 numeric(2,0), h11b numeric(2,0), h12a numeric(2,0), h12b numeric(2,0), h12c numeric(2,0), h12d numeric(2,0), h12e numeric(2,0), h12f numeric(2,0), h12g numeric(2,0), h12h numeric(2,0), h12i numeric(2,0), h12j numeric(2,0), h12k numeric(2,0), h12l numeric(2,0), h12m numeric(2,0), h12n numeric(2,0), h12o numeric(2,0), h12p numeric(2,0), h12q char(1),
      h12r char(1), h12s numeric(2,0), h12t numeric(2,0), h12u numeric(2,0), h12v numeric(2,0), h12w char(1), h12x numeric(2,0), h12y numeric(2,0), h12z numeric(2,0), h13 numeric(2,0), h13b numeric(2,0), h14 numeric(2,0), h15 numeric(2,0), h15a numeric(2,0), h15b numeric(2,0), h15c numeric(2,0), h15d numeric(2,0), h15e numeric(2,0), h15f numeric(2,0), h15g numeric(2,0), h15h numeric(2,0), h15i numeric(2,0), h15j char(1), h15k char(1), h15l char(1), h15m char(1), h20 numeric(2,0), h21a numeric(2,0), h21 numeric(2,0), h22 numeric(2,0),
      h31 numeric(2,0), h31b numeric(2,0), h31c numeric(2,0), h31d numeric(2,0), h31e numeric(2,0), h32a numeric(2,0), h32b numeric(2,0), h32c numeric(2,0), h32d numeric(2,0), h32e numeric(2,0), h32f numeric(2,0), h32g numeric(2,0), h32h numeric(2,0), h32i numeric(2,0), h32j numeric(2,0), h32k numeric(2,0), h32l numeric(2,0), h32m numeric(2,0), h32n numeric(2,0), h32o numeric(2,0), h32p numeric(2,0), h32q char(1), h32r char(1), h32s numeric(2,0), h32t numeric(2,0), h32u numeric(2,0), h32v numeric(2,0), h32w numeric(2,0), h32x numeric(2,0), h32y numeric(2,0),
      h32z numeric(2,0), h33 numeric(2,0), h33d numeric(3,0), h33m numeric(3,0), h33y numeric(5,0), h34 numeric(2,0), h35 char(1), h36a numeric(2,0), h36b numeric(2,0), h36c numeric(2,0), h36d numeric(2,0), h36e char(1), h36f char(1), h37a numeric(2,0), h37b numeric(2,0), h37c char(1), h37d numeric(2,0), h37e numeric(2,0), h37f char(1), h37g char(1), h37h numeric(2,0), h37i numeric(2,0), h37j numeric(2,0), h37k numeric(2,0), h37l numeric(2,0), h37m numeric(2,0), h37n numeric(2,0), h37o numeric(2,0), h37p numeric(2,0), h37x numeric(2,0),
      h37y numeric(2,0), h37z numeric(2,0), h38 numeric(2,0), h39 numeric(2,0), h40 char(1), h40d char(1), h40m char(1), h40y char(1), h41a char(1), h41b char(1), h42 numeric(2,0), h43 numeric(2,0), h44a numeric(3,0), h44b char(1), h44c char(1), h45 char(1), h46a numeric(3,0), h46b char(1), h47 numeric(2,0)
REC96_All (reader CSV_3)
    attributes: FileCode char(7), CASEID char(12), IDX96 number(2,0), S566 number(2,0), S567 number(3,0), S568A number(2,0), S568B number(2,0), S568C number(2,0), S568D number(2,0), S568E number(2,0), S569A number(2,0), S569B number(2,0), S569C number(2,0), S569D number(2,0), S569E number(2,0), S570A number(2,0), S570B number(2,0), S570C number(2,0), S570D number(2,0), S570X number(2,0), S571 number(2,0), S572A number(2,0), S572B number(2,0), S572C number(2,0), S572D number(2,0), S572X number(2,0), S572Y number(2,0), S573 number(3,0), S574 number(3,0)
    -> REC96_All (writer POSTGRES_1)
REC96_All (writer POSTGRES_1)
    attributes: filecode char(7), caseid char(12), idx96 numeric(2,0), s566 numeric(2,0), s567 numeric(3,0), s568a numeric(2,0), s568b numeric(2,0), s568c numeric(2,0), s568d numeric(2,0), s568e numeric(2,0), s569a numeric(2,0), s569b numeric(2,0), s569c numeric(2,0), s569d numeric(2,0), s569e numeric(2,0), s570a numeric(2,0), s570b numeric(2,0), s570c numeric(2,0), s570d numeric(2,0), s570x numeric(2,0), s571 numeric(2,0), s572a numeric(2,0), s572b numeric(2,0), s572c numeric(2,0), s572d numeric(2,0), s572x numeric(2,0), s572y numeric(2,0), s573 numeric(3,0), s574 numeric(3,0)
REC11_All (reader CSV_3)
    attributes: FileCode char(7), CASEID char(10), V101 number(2,0), V102 number(2,0), V103 char(1), V104 char(1), V105 char(1), V106 number(2,0), V107 number(2,0), V113 number(3,0), V115 number(4,0), V116 number(3,0), V119 number(2,0), V120 number(2,0), V121 number(2,0), V122 number(2,0), V123 number(2,0), V124 number(2,0), V125 char(1), V127 number(3,0), V128 number(3,0), V129 number(3,0), V130 number(2,0), V131 char(1), V133 number(3,0), V134 number(2,0), V135 number(2,0), V136 number(3,0), V137 number(2,0), V138 number(2,0),
      V139 number(3,0), V140 number(2,0), V141 number(2,0), V149 number(2,0), V150 number(3,0), V151 number(2,0), V152 number(3,0), V153 number(2,0), AWFACTT number(5,0), AWFACTU number(5,0), AWFACTR number(5,0), AWFACTE number(5,0), AWFACTW number(5,0), V155 number(2,0), V156 char(1), V157 number(2,0), V158 number(2,0), V159 number(2,0), V160 number(2,0), V161 number(3,0), V166 char(1), V167 char(1), V168 char(1), V190 number(2,0), V191 number(8,0), ML101 char(1)
    -> REC11_All (writer POSTGRES_1)
REC11_All (writer POSTGRES_1)
    attributes: filecode char(7), caseid char(10), v101 numeric(2,0), v102 numeric(2,0), v103 char(1), v104 char(1), v105 char(1), v106 numeric(2,0), v107 numeric(2,0), v113 numeric(3,0), v115 numeric(4,0), v116 numeric(3,0), v119 numeric(2,0), v120 numeric(2,0), v121 numeric(2,0), v122 numeric(2,0), v123 numeric(2,0), v124 numeric(2,0), v125 char(1), v127 numeric(3,0), v128 numeric(3,0), v129 numeric(3,0), v130 numeric(2,0), v131 char(1), v133 numeric(3,0), v134 numeric(2,0), v135 numeric(2,0), v136 numeric(3,0), v137 numeric(2,0), v138 numeric(2,0),
      v139 numeric(3,0), v140 numeric(2,0), v141 numeric(2,0), v149 numeric(2,0), v150 numeric(3,0), v151 numeric(2,0), v152 numeric(3,0), v153 numeric(2,0), awfactt numeric(5,0), awfactu numeric(5,0), awfactr numeric(5,0), awfacte numeric(5,0), awfactw numeric(5,0), v155 numeric(2,0), v156 char(1), v157 numeric(2,0), v158 numeric(2,0), v159 numeric(2,0), v160 numeric(2,0), v161 numeric(3,0), v166 char(1), v167 char(1), v168 char(1), v190 numeric(2,0), v191 numeric(8,0), ml101 char(1)
RECH10_All (reader CSV_3)
    attributes: FileCode char(7), HHID number(10,0), SLNWP number(2,0), SH216 number(3,0), SH218 number(3,0), SH220 number(4,0), SH220B char(4), SH221 char(4), SH221B number(4,0), SH221AH number(3,0), SH221AM number(3,0), SH222 number(2,0)
    -> RECH10_All (writer POSTGRES_1)
RECH10_All (writer POSTGRES_1)
    attributes: filecode char(7), hhid numeric(10,0), slnwp numeric(2,0), sh216 numeric(3,0), sh218 numeric(3,0), sh220 numeric(4,0), sh220b char(4), sh221 char(4), sh221b numeric(4,0), sh221ah numeric(3,0), sh221am numeric(3,0), sh222 numeric(2,0)
RECG1_All (reader CSV_3)
    attributes: FileCode char(7), CASEID char(9), G100 number(2,0), G101 number(2,0), G102 number(2,0), G103 number(2,0), G104 number(2,0), G105 number(2,0), G106 number(3,0), G107 number(3,0), G108 number(3,0), G109 char(1), G110 char(1), G111 char(1), G112 char(1), G113 char(1), G114 char(1), G115 char(1), G116 char(1), G117A char(1), G117B char(1), G117C char(1), G117D char(1), G117E char(1), G117F char(1), G117G char(1), G117H char(1), G117I char(1), G117J char(1), G117X char(1),
      G117Y char(1), G118 number(2,0), G119 number(2,0)
    -> RECG1_All (writer POSTGRES_1)
RECG1_All (writer POSTGRES_1)
    attributes: filecode char(7), caseid char(9), g100 numeric(2,0), g101 numeric(2,0), g102 numeric(2,0), g103 numeric(2,0), g104 numeric(2,0), g105 numeric(2,0), g106 numeric(3,0), g107 numeric(3,0), g108 numeric(3,0), g109 char(1), g110 char(1), g111 char(1), g112 char(1), g113 char(1), g114 char(1), g115 char(1), g116 char(1), g117a char(1), g117b char(1), g117c char(1), g117d char(1), g117e char(1), g117f char(1), g117g char(1), g117h char(1), g117i char(1), g117j char(1), g117x char(1),
      g117y char(1), g118 numeric(2,0), g119 numeric(2,0)
RECGC_All (reader CSV_3)
    attributes: FileCode char(7), CASEID char(10), G100 number(2,0), G101 number(2,0), G102 number(2,0), G103 number(2,0), G104 number(2,0), G105 number(2,0), G106 number(3,0), G107 number(3,0), G108 number(3,0), G109 number(3,0), G110 number(2,0), G111 number(2,0), G112 number(2,0), G113 number(3,0), G114 number(3,0), G115 char(1), G116 number(2,0), G117A char(1), G117B char(1), G117C char(1), G117D char(1), G117E char(1), G117F char(1), G117G char(1), G117H char(1), G117I char(1), G117J char(1), G117X char(1),
      G117Y char(1), G118 char(1), G119 number(2,0)
    -> RECGC_All (writer POSTGRES_1)
RECGC_All (writer POSTGRES_1)
    attributes: filecode char(7), caseid char(10), g100 numeric(2,0), g101 numeric(2,0), g102 numeric(2,0), g103 numeric(2,0), g104 numeric(2,0), g105 numeric(2,0), g106 numeric(3,0), g107 numeric(3,0), g108 numeric(3,0), g109 numeric(3,0), g110 numeric(2,0), g111 numeric(2,0), g112 numeric(2,0), g113 numeric(3,0), g114 numeric(3,0), g115 char(1), g116 numeric(2,0), g117a char(1), g117b char(1), g117c char(1), g117d char(1), g117e char(1), g117f char(1), g117g char(1), g117h char(1), g117i char(1), g117j char(1), g117x char(1),
      g117y char(1), g118 char(1), g119 numeric(2,0)
RECH6_All (reader CSV_3)
    attributes: FileCode char(7), HHID char(7), HC0 number(3,0), HC1 number(3,0), HC2 number(5,0), HC3 number(5,0), HC4 number(5,0), HC5 number(5,0), HC6 number(6,0), HC7 number(5,0), HC8 number(5,0), HC9 number(6,0), HC10 number(5,0), HC11 number(5,0), HC12 number(6,0), HC13 number(2,0), HC15 number(2,0), HC16 number(3,0), HC17 number(3,0), HC18 number(3,0), HC19 number(5,0), HC27 number(2,0), HC30 number(3,0), HC31 number(5,0), HC32 number(5,0), HC33 number(2,0), HC51 number(3,0), HC52 number(2,0), HC53 number(4,0), HC55 number(2,0),
      HC56 number(4,0), HC57 number(2,0), HC58 char(1), HC60 number(4,0), HC61 number(2,0), HC62 number(3,0), HC63 number(4,0), HC64 number(3,0), SHB13 number(2,0), HC68 number(5,0), HC70 number(5,0), HC71 number(5,0), HC72 number(5,0), HC73 number(5,0)
    -> RECH6_All (writer POSTGRES_1)
RECH6_All (writer POSTGRES_1)
    attributes: filecode char(7), hhid char(7), hc0 numeric(3,0), hc1 numeric(3,0), hc2 numeric(5,0), hc3 numeric(5,0), hc4 numeric(5,0), hc5 numeric(5,0), hc6 numeric(6,0), hc7 numeric(5,0), hc8 numeric(5,0), hc9 numeric(6,0), hc10 numeric(5,0), hc11 numeric(5,0), hc12 numeric(6,0), hc13 numeric(2,0), hc15 numeric(2,0), hc16 numeric(3,0), hc17 numeric(3,0), hc18 numeric(3,0), hc19 numeric(5,0), hc27 numeric(2,0), hc30 numeric(3,0), hc31 numeric(5,0), hc32 numeric(5,0), hc33 numeric(2,0), hc51 numeric(3,0), hc52 numeric(2,0), hc53 numeric(4,0), hc55 numeric(2,0),
      hc56 numeric(4,0), hc57 numeric(2,0), hc58 char(1), hc60 numeric(4,0), hc61 numeric(2,0), hc62 numeric(3,0), hc63 numeric(4,0), hc64 numeric(3,0), shb13 numeric(2,0), hc68 numeric(5,0), hc70 numeric(5,0), hc71 numeric(5,0), hc72 numeric(5,0), hc73 numeric(5,0)
REC32_All (reader CSV_3)
    attributes: FileCode char(7), CASEID char(10), V310 char(1), V311 char(1), V312 number(3,0), V313 number(2,0), V315 number(3,0), V316 number(5,0), V317 number(5,0), V318 number(2,0), V319 number(2,0), V320 number(2,0), V321 number(2,0), V322 number(2,0), V323 number(3,0), V323A number(3,0), V325A char(1), V326 number(3,0), V327 number(2,0), V337 number(3,0), V359 number(3,0), V360 number(3,0), V361 number(2,0), V362 number(2,0), V363 number(3,0), V364 number(2,0), V367 number(2,0), V372 number(2,0), V372A number(2,0), V375A char(1),
      V376 number(3,0), V376A char(1), V379 char(1), V380 char(1), V384A number(2,0), V384B number(2,0), V384C number(2,0), V393 char(1), V394 char(1), V395 char(1), V3A00A number(2,0), V3A00B number(2,0), V3A00C number(2,0), V3A00D number(2,0), V3A00E number(2,0), V3A00F number(2,0), V3A00G number(2,0), V3A00H number(2,0), V3A00I number(2,0), V3A00J number(2,0), V3A00K number(2,0), V3A00L number(2,0), V3A00M number(2,0), V3A00N number(2,0), V3A00O number(2,0), V3A00P char(1), V3A00Q char(1), V3A00R char(1), V3A00S number(2,0), V3A00T char(1),
      V3A00U number(2,0), V3A00V number(2,0), V3A00W number(2,0), V3A00X number(2,0), V3A00Y number(2,0), V3A00Z number(2,0), V3A01 char(1), V3A02 char(1), V3A03 char(1), V3A04 char(1), V3A05 char(1), V3A06 char(1), V3A07 number(3,0), V3A08A char(1), V3A08B number(2,0), V3A08C number(2,0), V3A08D number(2,0), V3A08E number(2,0), V3A08F number(2,0), V3A08G number(2,0), V3A08H number(2,0), V3A08I number(2,0), V3A08J number(2,0), V3A08K number(2,0), V3A08L number(2,0), V3A08M number(2,0), V3A08N number(2,0), V3A08O char(1), V3A08P number(2,0), V3A08Q number(2,0),
      V3A08R number(2,0), V3A08S number(2,0), V3A08T number(2,0), V3A08U number(2,0), V3A08V number(2,0), V3A08W char(1), V3A08AA char(1), V3A08AB char(1), V3A08AC char(1), V3A08AD char(1), V3A08X number(2,0), V3A08Z number(2,0), V3A09A char(1), V3A09B char(1)
    -> REC32_All (writer POSTGRES_1)
REC32_All (writer POSTGRES_1)
    attributes: filecode char(7), caseid char(10), v310 char(1), v311 char(1), v312 numeric(3,0), v313 numeric(2,0), v315 numeric(3,0), v316 numeric(5,0), v317 numeric(5,0), v318 numeric(2,0), v319 numeric(2,0), v320 numeric(2,0), v321 numeric(2,0), v322 numeric(2,0), v323 numeric(3,0), v323a numeric(3,0), v325a char(1), v326 numeric(3,0), v327 numeric(2,0), v337 numeric(3,0), v359 numeric(3,0), v360 numeric(3,0), v361 numeric(2,0), v362 numeric(2,0), v363 numeric(3,0), v364 numeric(2,0), v367 numeric(2,0), v372 numeric(2,0), v372a numeric(2,0), v375a char(1),
      v376 numeric(3,0), v376a char(1), v379 char(1), v380 char(1), v384a numeric(2,0), v384b numeric(2,0), v384c numeric(2,0), v393 char(1), v394 char(1), v395 char(1), v3a00a numeric(2,0), v3a00b numeric(2,0), v3a00c numeric(2,0), v3a00d numeric(2,0), v3a00e numeric(2,0), v3a00f numeric(2,0), v3a00g numeric(2,0), v3a00h numeric(2,0), v3a00i numeric(2,0), v3a00j numeric(2,0), v3a00k numeric(2,0), v3a00l numeric(2,0), v3a00m numeric(2,0), v3a00n numeric(2,0), v3a00o numeric(2,0), v3a00p char(1), v3a00q char(1), v3a00r char(1), v3a00s numeric(2,0), v3a00t char(1),
      v3a00u numeric(2,0), v3a00v numeric(2,0), v3a00w numeric(2,0), v3a00x numeric(2,0), v3a00y numeric(2,0), v3a00z numeric(2,0), v3a01 char(1), v3a02 char(1), v3a03 char(1), v3a04 char(1), v3a05 char(1), v3a06 char(1), v3a07 numeric(3,0), v3a08a char(1), v3a08b numeric(2,0), v3a08c numeric(2,0), v3a08d numeric(2,0), v3a08e numeric(2,0), v3a08f numeric(2,0), v3a08g numeric(2,0), v3a08h numeric(2,0), v3a08i numeric(2,0), v3a08j numeric(2,0), v3a08k numeric(2,0), v3a08l numeric(2,0), v3a08m numeric(2,0), v3a08n numeric(2,0), v3a08o char(1), v3a08p numeric(2,0), v3a08q numeric(2,0),
      v3a08r numeric(2,0), v3a08s numeric(2,0), v3a08t numeric(2,0), v3a08u numeric(2,0), v3a08v numeric(2,0), v3a08w char(1), v3a08aa char(1), v3a08ab char(1), v3a08ac char(1), v3a08ad char(1), v3a08x numeric(2,0), v3a08z numeric(2,0), v3a09a char(1), v3a09b char(1)
RECHPC_All (reader CSV_3)
    attributes: FileCode char(7), HHID char(6), HPCIDX number(3,0), SH198C number(2,0), SH198D number(2,0)
    -> RECHPC_All (writer POSTGRES_1)
RECHPC_All (writer POSTGRES_1)
    attributes: filecode char(7), hhid char(6), hpcidx numeric(3,0), sh198c numeric(2,0), sh198d numeric(2,0)
RECHMLS_All (reader CSV_3)
    attributes: FileCode char(7), HHID char(7), SHMLIDX number(2,0), SH136 number(2,0), SH139A number(3,0), SH139B number(3,0), SH139C number(3,0), SH139D number(3,0), SH139E number(3,0)
    -> RECHMLS_All (writer POSTGRES_1)
RECHMLS_All (writer POSTGRES_1)
    attributes: filecode char(7), hhid char(7), shmlidx numeric(2,0), sh136 numeric(2,0), sh139a numeric(3,0), sh139b numeric(3,0), sh139c numeric(3,0), sh139d numeric(3,0), sh139e numeric(3,0)
RECH5CS_All (reader CSV_3)
    attributes: FileCode char(7), HHID char(7), IDX5CS number(3,0), SH224 number(2,0), SH224I number(4,0), SH234 number(2,0), SH235 number(2,0), SH235A number(2,0), SH242 number(2,0), SH242I number(4,0), SH248 number(2,0), SH251BC char(6), SH251 number(2,0), SH251A number(9,0), SH251AD number(3,0), SH251AM number(3,0), SH251AY number(5,0), SH251B number(5,0), SH251BH number(3,0), SH251BM number(3,0)
    -> RECH5CS_All (writer POSTGRES_1)
RECH5CS_All (writer POSTGRES_1)
    attributes: filecode char(7), hhid char(7), idx5cs numeric(3,0), sh224 numeric(2,0), sh224i numeric(4,0), sh234 numeric(2,0), sh235 numeric(2,0), sh235a numeric(2,0), sh242 numeric(2,0), sh242i numeric(4,0), sh248 numeric(2,0), sh251bc char(6), sh251 numeric(2,0), sh251a numeric(9,0), sh251ad numeric(3,0), sh251am numeric(3,0), sh251ay numeric(5,0), sh251b numeric(5,0), sh251bh numeric(3,0), sh251bm numeric(3,0)
RECHMA_All (reader CSV_3)
    attributes: FileCode char(7), HHID char(7), HB0 number(3,0), HB1 number(3,0), HB2 number(5,0), HB3 number(5,0), HB4 number(5,0), HB5 number(5,0), HB6 number(6,0), HB11 number(5,0), HB12 number(6,0), HB12A number(6,0), HB12B number(6,0), HB13 number(2,0), HB32 number(5,0), HB33 number(2,0), HB35 number(3,0), HB40 number(5,0), HB41 number(5,0), HB50 number(2,0), HB51 number(3,0), HB52 number(2,0), HB53 number(4,0), HB55 number(2,0), HB56 number(4,0), HB57 number(2,0), HB58 char(1), HB60 number(2,0), HB61 number(2,0), HB62 char(6),
      HB63 number(2,0), HB64 number(2,0), HB65 number(2,0), HB66 number(2,0), HB67 number(3,0), HB68 number(2,0), HB69 number(8,0), HB70 number(4,0)
    -> RECHMA_All (writer POSTGRES_1)
RECHMA_All (writer POSTGRES_1)
    attributes: filecode char(7), hhid char(7), hb0 numeric(3,0), hb1 numeric(3,0), hb2 numeric(5,0), hb3 numeric(5,0), hb4 numeric(5,0), hb5 numeric(5,0), hb6 numeric(6,0), hb11 numeric(5,0), hb12 numeric(6,0), hb12a numeric(6,0), hb12b numeric(6,0), hb13 numeric(2,0), hb32 numeric(5,0), hb33 numeric(2,0), hb35 numeric(3,0), hb40 numeric(5,0), hb41 numeric(5,0), hb50 numeric(2,0), hb51 numeric(3,0), hb52 numeric(2,0), hb53 numeric(4,0), hb55 numeric(2,0), hb56 numeric(4,0), hb57 numeric(2,0), hb58 char(1), hb60 numeric(2,0), hb61 numeric(2,0), hb62 char(6),
      hb63 numeric(2,0), hb64 numeric(2,0), hb65 numeric(2,0), hb66 numeric(2,0), hb67 numeric(3,0), hb68 numeric(2,0), hb69 numeric(8,0), hb70 numeric(4,0)
REC91_All (reader CSV_3)
    attributes: FileCode char(7), CASEID char(10), S28DAYS number(2,0), S5YEARS number(2,0), S103A number(2,0), S104A number(2,0), S112A number(2,0), S112B number(2,0), S114A number(2,0), S114B number(2,0), S114C number(2,0), S114D number(2,0), S114E number(2,0), S114F number(2,0), S114G number(2,0), S114GX number(3,0), S223A number(2,0), S223B number(2,0), S229A number(2,0), S229B number(2,0), S229C number(2,0), S229D number(3,0), S306A number(2,0), S325J number(2,0), S325M number(2,0), S325N number(2,0), S325O number(2,0), S325A number(2,0), S325B number(2,0), S325CA number(2,0),
      S325CB number(2,0), S325CC number(2,0), S325CD number(2,0), S325CE number(2,0), S325CF number(2,0), S325CG number(2,0), S325CH number(2,0), S325CX number(2,0), S325CZ number(2,0), S325D number(2,0), S325E number(2,0), S325FA number(2,0), S325FB number(2,0), S325FC number(2,0), S325FD number(2,0), S325FE number(2,0), S325FF number(2,0), S325FH number(2,0), S325FX number(2,0), S325FZ number(2,0), S326 number(2,0), S326AA number(2,0), S326AB number(2,0), S326AC number(2,0), S326AX number(2,0), S326B number(3,0), S326C number(2,0), S506A char(1), S604A number(3,0), S616 number(3,0),
      S714AA number(2,0), S714BA number(2,0), S714BB number(2,0), S714BC number(2,0), S714D number(2,0), S714E number(2,0), S803A number(2,0), S823 number(2,0), S823A number(2,0), S823B number(2,0), S906A number(2,0), S906B number(2,0), S937A number(2,0), S937B number(2,0), S945O number(2,0), S945A number(2,0), S1001 number(2,0), S1002 number(2,0), S1003 number(2,0), S1004 number(2,0), S1005 number(2,0), SCORE number(3,0), AWFACTE2 number(6,0), AWFACTE3 number(6,0)
    -> REC91_All (writer POSTGRES_1)
REC91_All (writer POSTGRES_1)
    attributes: filecode char(7), caseid char(10), s28days numeric(2,0), s5years numeric(2,0), s103a numeric(2,0), s104a numeric(2,0), s112a numeric(2,0), s112b numeric(2,0), s114a numeric(2,0), s114b numeric(2,0), s114c numeric(2,0), s114d numeric(2,0), s114e numeric(2,0), s114f numeric(2,0), s114g numeric(2,0), s114gx numeric(3,0), s223a numeric(2,0), s223b numeric(2,0), s229a numeric(2,0), s229b numeric(2,0), s229c numeric(2,0), s229d numeric(3,0), s306a numeric(2,0), s325j numeric(2,0), s325m numeric(2,0), s325n numeric(2,0), s325o numeric(2,0), s325a numeric(2,0), s325b numeric(2,0), s325ca numeric(2,0),
      s325cb numeric(2,0), s325cc numeric(2,0), s325cd numeric(2,0), s325ce numeric(2,0), s325cf numeric(2,0), s325cg numeric(2,0), s325ch numeric(2,0), s325cx numeric(2,0), s325cz numeric(2,0), s325d numeric(2,0), s325e numeric(2,0), s325fa numeric(2,0), s325fb numeric(2,0), s325fc numeric(2,0), s325fd numeric(2,0), s325fe numeric(2,0), s325ff numeric(2,0), s325fh numeric(2,0), s325fx numeric(2,0), s325fz numeric(2,0), s326 numeric(2,0), s326aa numeric(2,0), s326ab numeric(2,0), s326ac numeric(2,0), s326ax numeric(2,0), s326b numeric(3,0), s326c numeric(2,0), s506a char(1), s604a numeric(3,0), s616 numeric(3,0),
      s714aa numeric(2,0), s714ba numeric(2,0), s714bb numeric(2,0), s714bc numeric(2,0), s714d numeric(2,0), s714e numeric(2,0), s803a numeric(2,0), s823 numeric(2,0), s823a numeric(2,0), s823b numeric(2,0), s906a numeric(2,0), s906b numeric(2,0), s937a numeric(2,0), s937b numeric(2,0), s945o numeric(2,0), s945a numeric(2,0), s1001 numeric(2,0), s1002 numeric(2,0), s1003 numeric(2,0), s1004 numeric(2,0), s1005 numeric(2,0), score numeric(3,0), awfacte2 numeric(6,0), awfacte3 numeric(6,0)
REC21_All (reader CSV_3)
    attributes: FileCode char(7), CASEID char(10), BIDX number(3,0), BORD number(3,0), B0 number(2,0), B1 number(3,0), B2 number(5,0), B3 number(5,0), B4 number(2,0), B5 number(2,0), B6 number(4,0), B7 number(4,0), B8 number(3,0), B9 number(2,0), B10 number(2,0), B11 number(4,0), B12 number(4,0), B13 number(2,0), B15 number(2,0), B16 number(3,0)
    -> REC21_All (writer POSTGRES_1)
REC21_All (writer POSTGRES_1)
    attributes: filecode char(7), caseid char(10), bidx numeric(3,0), bord numeric(3,0), b0 numeric(2,0), b1 numeric(3,0), b2 numeric(5,0), b3 numeric(5,0), b4 numeric(2,0), b5 numeric(2,0), b6 numeric(4,0), b7 numeric(4,0), b8 numeric(3,0), b9 numeric(2,0), b10 numeric(2,0), b11 numeric(4,0), b12 numeric(4,0), b13 numeric(2,0), b15 numeric(2,0), b16 numeric(3,0)
RECHCHL_All (reader CSV_3)
    attributes: FileCode char(7), HHID char(10), IDXCHL number(3,0), CHL1 number(2,0), CHL2 number(3,0), CHL3 number(2,0), CHL4 number(3,0), CHL5 number(2,0), CHL6 number(3,0), CHL7 number(2,0), CHL8 number(3,0)
    -> RECHCHL_All (writer POSTGRES_1)
RECHCHL_All (writer POSTGRES_1)
    attributes: filecode char(7), hhid char(10), idxchl numeric(3,0), chl1 numeric(2,0), chl2 numeric(3,0), chl3 numeric(2,0), chl4 numeric(3,0), chl5 numeric(2,0), chl6 numeric(3,0), chl7 numeric(2,0), chl8 numeric(3,0)
RECH1_All (reader CSV_3)
    attributes: FileCode char(7), HHID char(6), HVIDX number(3,0), HV101 number(3,0), HV102 number(2,0), HV103 number(2,0), HV104 number(2,0), HV105 number(3,0), HV106 number(2,0), HV107 number(2,0), HV108 number(3,0), HV109 number(2,0), HV110 char(1), HV111 char(1), HV112 char(1), HV113 char(1), HV114 char(1), HV115 char(1), HV116 number(2,0), HV117 number(2,0), HV118 number(2,0), HV120 number(2,0), HV121 number(2,0), HV122 number(2,0), HV123 number(2,0), HV124 number(3,0), HV125 char(1), HV126 char(1), HV127 char(1), HV128 char(1),
      HV129 char(1), HV140 number(2,0)
    -> RECH1_All (writer POSTGRES_1)
RECH1_All (writer POSTGRES_1)
    attributes: filecode char(7), hhid char(6), hvidx numeric(3,0), hv101 numeric(3,0), hv102 numeric(2,0), hv103 numeric(2,0), hv104 numeric(2,0), hv105 numeric(3,0), hv106 numeric(2,0), hv107 numeric(2,0), hv108 numeric(3,0), hv109 numeric(2,0), hv110 char(1), hv111 char(1), hv112 char(1), hv113 char(1), hv114 char(1), hv115 char(1), hv116 numeric(2,0), hv117 numeric(2,0), hv118 numeric(2,0), hv120 numeric(2,0), hv121 numeric(2,0), hv122 numeric(2,0), hv123 numeric(2,0), hv124 numeric(3,0), hv125 char(1), hv126 char(1), hv127 char(1), hv128 char(1),
      hv129 char(1), hv140 numeric(2,0)
RECHC_All (reader CSV_3)
    attributes: FileCode char(7), HHID char(7), SHCOLC number(2,0), SH202 number(3,0), SH205 number(5,0), SH206 number(5,0), SH212 number(4,0)
    -> RECHC_All (writer POSTGRES_1)
RECHC_All (writer POSTGRES_1)
    attributes: filecode char(7), hhid char(7), shcolc numeric(2,0), sh202 numeric(3,0), sh205 numeric(5,0), sh206 numeric(5,0), sh212 numeric(4,0)
REC80_All (reader CSV_3)
    attributes: FileCode char(7), CASEID char(10), V820 char(1), V821A char(1), V821B char(1), V821C char(1), V822 char(1), V823 number(2,0), V824 char(1), V825 char(1), V826 char(1), V826A char(1), V827 char(1), V828 char(1), V829 char(1), V830 char(1), V831 char(1), V832B char(1), V832C char(1), V833A char(1), V833B char(1), V833C char(1), V834A char(1), V834B char(1), V834C char(1), V835A char(1), V835B char(1), V835C char(1), V836 char(1), V837 char(1),
      V838A char(1), V838B char(1), V838C char(1), V839 char(1), V839A char(1), V840 char(1), V840A char(1), V841 char(1), V841A char(1), V842 char(1), V843 char(1), V844 char(1), V845 char(1), V846 char(1), V847 char(1), V848 char(1), V849 char(1), V850A char(1), V850B char(1), V851A char(1), V851B char(1), V851C char(1), V851D char(1), V851E char(1), V851F char(1), V851G char(1), V851H char(1), V851I char(1), V851J char(1), V851K char(1),
      V851L char(1), V852A char(1), V852B char(1), V852C char(1), V853A char(1), V853B char(1), V853C char(1), V854A char(1), V854B char(1), V855 char(1)
    -> REC80_All (writer POSTGRES_1)
REC80_All (writer POSTGRES_1)
    attributes: filecode char(7), caseid char(10), v820 char(1), v821a char(1), v821b char(1), v821c char(1), v822 char(1), v823 numeric(2,0), v824 char(1), v825 char(1), v826 char(1), v826a char(1), v827 char(1), v828 char(1), v829 char(1), v830 char(1), v831 char(1), v832b char(1), v832c char(1), v833a char(1), v833b char(1), v833c char(1), v834a char(1), v834b char(1), v834c char(1), v835a char(1), v835b char(1), v835c char(1), v836 char(1), v837 char(1),
      v838a char(1), v838b char(1), v838c char(1), v839 char(1), v839a char(1), v840 char(1), v840a char(1), v841 char(1), v841a char(1), v842 char(1), v843 char(1), v844 char(1), v845 char(1), v846 char(1), v847 char(1), v848 char(1), v849 char(1), v850a char(1), v850b char(1), v851a char(1), v851b char(1), v851c char(1), v851d char(1), v851e char(1), v851f char(1), v851g char(1), v851h char(1), v851i char(1), v851j char(1), v851k char(1),
      v851l char(1), v852a char(1), v852b char(1), v852c char(1), v853a char(1), v853b char(1), v853c char(1), v854a char(1), v854b char(1), v855 char(1)
REC42_All (reader CSV_3)
    attributes: FileCode char(7), CASEID char(10), V401 number(2,0), V404 number(2,0), V405 number(2,0), V406 number(2,0), V407 char(1), V408 char(1), V409 number(2,0), V409A char(1), V410 number(2,0), V410A char(1), V411 number(2,0), V411A number(2,0), V412 char(1), V412A number(2,0), V412B char(1), V412C char(1), V413 number(2,0), V413A char(1), V413B char(1), V413C char(1), V413D char(1), V414A char(1), V414B char(1), V414C char(1), V414D char(1), V414E number(2,0), V414F number(2,0), V414G number(2,0),
      V414H number(2,0), V414I number(2,0), V414J number(2,0), V414K number(2,0), V414L number(2,0), V414M number(2,0), V414N number(2,0), V414O number(2,0), V414P number(2,0), V414Q char(1), V414R char(1), V414S number(2,0), V414T char(1), V414U char(1), V414V number(2,0), V414W char(1), V415 number(2,0), V416 char(1), V417 number(2,0), V418 number(2,0), V419 number(2,0), V420 char(1), V421 char(1), V426 number(4,0), V437 number(5,0), V438 number(5,0), V439 number(5,0), V440 number(5,0), V441 number(6,0), V442 number(6,0),
      V443 number(6,0), V444 number(6,0), V444A number(5,0), V445 number(5,0), V446 number(5,0), V447 number(2,0), V447A number(3,0), V452A char(1), V452B char(1), V452C number(2,0), V453 number(4,0), V454 number(2,0), V455 number(2,0), V456 number(4,0), V457 number(2,0), V458 char(1), V459 char(1), V460 char(1), V461 char(1), V462 char(1), V463A char(1), V463B char(1), V463C char(1), V463D char(1), V463E char(1), V463F char(1), V463G char(1), V463X char(1), V463Z char(1), V464 char(1),
      V465 char(1), V466 char(1), V467A char(1), V467B char(1), V467C char(1), V467D char(1), V467E char(1), V467F char(1), V467G char(1), V467H char(1), V467I char(1), V467J char(1), V467K char(1), V467L char(1), V467M char(1), V468 number(2,0), V469E number(2,0), V469F number(2,0), V469X number(2,0), V471A char(1), V471B char(1), V471C char(1), V471D char(1), V471E char(1), V471F char(1), V471G char(1), V472A char(1), V472B char(1), V472C char(1), V472D char(1),
      V472E char(1), V472F char(1), V472G char(1), V472H char(1), V472I char(1), V472J char(1), V472K char(1), V472L char(1), V472M char(1), V472N char(1), V472O char(1), V472P char(1), V472Q char(1), V472R char(1), V472S char(1), V472T char(1), V472U char(1), V473A char(1), V473B char(1), V474 char(1), V474A char(1), V474B char(1), V474C char(1), V474D char(1), V474E char(1), V474F char(1), V474G char(1), V474H char(1), V474I char(1), V474J char(1),
      V474X char(1), V474Z char(1), V475 char(1), V476 char(1), V477 char(1), V478 char(1), V479 char(1), V480 char(1), V481 char(1), V481A char(1), V481B char(1), V481C char(1), V481D char(1), V481E char(1), V481F char(1), V481G char(1), V481H char(1), V481X char(1), V482A char(1), V482B char(1), V482C char(1)
    -> REC42_All (writer POSTGRES_1)
REC42_All (writer POSTGRES_1)
    attributes: filecode char(7), caseid char(10), v401 numeric(2,0), v404 numeric(2,0), v405 numeric(2,0), v406 numeric(2,0), v407 char(1), v408 char(1), v409 numeric(2,0), v409a char(1), v410 numeric(2,0), v410a char(1), v411 numeric(2,0), v411a numeric(2,0), v412 char(1), v412a numeric(2,0), v412b char(1), v412c char(1), v413 numeric(2,0), v413a char(1), v413b char(1), v413c char(1), v413d char(1), v414a char(1), v414b char(1), v414c char(1), v414d char(1), v414e numeric(2,0), v414f numeric(2,0), v414g numeric(2,0),
      v414h numeric(2,0), v414i numeric(2,0), v414j numeric(2,0), v414k numeric(2,0), v414l numeric(2,0), v414m numeric(2,0), v414n numeric(2,0), v414o numeric(2,0), v414p numeric(2,0), v414q char(1), v414r char(1), v414s numeric(2,0), v414t char(1), v414u char(1), v414v numeric(2,0), v414w char(1), v415 numeric(2,0), v416 char(1), v417 numeric(2,0), v418 numeric(2,0), v419 numeric(2,0), v420 char(1), v421 char(1), v426 numeric(4,0), v437 numeric(5,0), v438 numeric(5,0), v439 numeric(5,0), v440 numeric(5,0), v441 numeric(6,0), v442 numeric(6,0),
      v443 numeric(6,0), v444 numeric(6,0), v444a numeric(5,0), v445 numeric(5,0), v446 numeric(5,0), v447 numeric(2,0), v447a numeric(3,0), v452a char(1), v452b char(1), v452c numeric(2,0), v453 numeric(4,0), v454 numeric(2,0), v455 numeric(2,0), v456 numeric(4,0), v457 numeric(2,0), v458 char(1), v459 char(1), v460 char(1), v461 char(1), v462 char(1), v463a char(1), v463b char(1), v463c char(1), v463d char(1), v463e char(1), v463f char(1), v463g char(1), v463x char(1), v463z char(1), v464 char(1),
      v465 char(1), v466 char(1), v467a char(1), v467b char(1), v467c char(1), v467d char(1), v467e char(1), v467f char(1), v467g char(1), v467h char(1), v467i char(1), v467j char(1), v467k char(1), v467l char(1), v467m char(1), v468 numeric(2,0), v469e numeric(2,0), v469f numeric(2,0), v469x numeric(2,0), v471a char(1), v471b char(1), v471c char(1), v471d char(1), v471e char(1), v471f char(1), v471g char(1), v472a char(1), v472b char(1), v472c char(1), v472d char(1),
      v472e char(1), v472f char(1), v472g char(1), v472h char(1), v472i char(1), v472j char(1), v472k char(1), v472l char(1), v472m char(1), v472n char(1), v472o char(1), v472p char(1), v472q char(1), v472r char(1), v472s char(1), v472t char(1), v472u char(1), v473a char(1), v473b char(1), v474 char(1), v474a char(1), v474b char(1), v474c char(1), v474d char(1), v474e char(1), v474f char(1), v474g char(1), v474h char(1), v474i char(1), v474j char(1),
      v474x char(1), v474z char(1), v475 char(1), v476 char(1), v477 char(1), v478 char(1), v479 char(1), v480 char(1), v481 char(1), v481a char(1), v481b char(1), v481c char(1), v481d char(1), v481e char(1), v481f char(1), v481g char(1), v481h char(1), v481x char(1), v482a char(1), v482b char(1), v482c char(1)
REC95_All (reader CSV_3)
    attributes: FileCode char(7), CASEID char(10), IDX95 number(2,0), S506AD number(3,0), S506AM number(3,0), S506AY number(5,0), SHB1 number(3,0), SHB1D number(3,0), SHB1M number(5,0), SHB1Y number(5,0), SHB2 number(3,0), SHB2D number(5,0), SHB2M number(3,0), SHB2Y number(5,0), SHB3 number(2,0), SHB3D number(3,0), SHB3M number(3,0), SHB3Y number(5,0), S510J number(2,0), S519J number(2,0), S522C number(2,0), S522D number(2,0), S523A number(2,0), S523B number(2,0), S523C number(2,0), S523D number(2,0), S523E number(2,0), S523F number(2,0), S523G number(2,0), S523H number(2,0),
      S523I number(2,0), S523J number(2,0), S523K number(2,0), S523L number(2,0), S523M number(2,0), S523N number(2,0), S523O number(2,0), S523P number(2,0), S523Q number(2,0), S523R number(2,0), S523S number(2,0), S523T number(2,0), S523U number(2,0), S523V number(2,0), S523W number(2,0), S523X number(2,0), S536A number(2,0), S536K number(2,0), S536B number(3,0), S536C number(3,0), S536D number(3,0), S538O number(2,0), S538P number(2,0), S539 number(2,0), S540A number(2,0), S540B number(2,0), S540C number(2,0), S540D number(2,0), S540E number(2,0), S540F number(2,0),
      S540G number(2,0), S540H number(2,0), S540I number(2,0), S540J number(2,0), S540K number(2,0), S540L number(2,0), S540W number(2,0), S540X number(2,0), S541A number(2,0), S541B number(2,0), S541C number(2,0), S541D number(2,0), S541E number(2,0), S541F number(2,0), S541G number(2,0), S541H number(2,0), S541I number(2,0), S541J number(2,0), S541K number(2,0), S541L number(2,0), S541M number(2,0), S541N number(2,0), S541O number(2,0), S541P number(2,0), S541Q number(2,0), S541R number(2,0), S541S number(2,0), S541T number(2,0), S541U number(2,0), S541V number(2,0),
      S541W number(2,0), S541X number(2,0), S541Y number(2,0)
    -> REC95_All (writer POSTGRES_1)
REC95_All (writer POSTGRES_1)
    attributes: filecode char(7), caseid char(10), idx95 numeric(2,0), s506ad numeric(3,0), s506am numeric(3,0), s506ay numeric(5,0), shb1 numeric(3,0), shb1d numeric(3,0), shb1m numeric(5,0), shb1y numeric(5,0), shb2 numeric(3,0), shb2d numeric(5,0), shb2m numeric(3,0), shb2y numeric(5,0), shb3 numeric(2,0), shb3d numeric(3,0), shb3m numeric(3,0), shb3y numeric(5,0), s510j numeric(2,0), s519j numeric(2,0), s522c numeric(2,0), s522d numeric(2,0), s523a numeric(2,0), s523b numeric(2,0), s523c numeric(2,0), s523d numeric(2,0), s523e numeric(2,0), s523f numeric(2,0), s523g numeric(2,0), s523h numeric(2,0),
      s523i numeric(2,0), s523j numeric(2,0), s523k numeric(2,0), s523l numeric(2,0), s523m numeric(2,0), s523n numeric(2,0), s523o numeric(2,0), s523p numeric(2,0), s523q numeric(2,0), s523r numeric(2,0), s523s numeric(2,0), s523t numeric(2,0), s523u numeric(2,0), s523v numeric(2,0), s523w numeric(2,0), s523x numeric(2,0), s536a numeric(2,0), s536k numeric(2,0), s536b numeric(3,0), s536c numeric(3,0), s536d numeric(3,0), s538o numeric(2,0), s538p numeric(2,0), s539 numeric(2,0), s540a numeric(2,0), s540b numeric(2,0), s540c numeric(2,0), s540d numeric(2,0), s540e numeric(2,0), s540f numeric(2,0),
      s540g numeric(2,0), s540h numeric(2,0), s540i numeric(2,0), s540j numeric(2,0), s540k numeric(2,0), s540l numeric(2,0), s540w numeric(2,0), s540x numeric(2,0), s541a numeric(2,0), s541b numeric(2,0), s541c numeric(2,0), s541d numeric(2,0), s541e numeric(2,0), s541f numeric(2,0), s541g numeric(2,0), s541h numeric(2,0), s541i numeric(2,0), s541j numeric(2,0), s541k numeric(2,0), s541l numeric(2,0), s541m numeric(2,0), s541n numeric(2,0), s541o numeric(2,0), s541p numeric(2,0), s541q numeric(2,0), s541r numeric(2,0), s541s numeric(2,0), s541t numeric(2,0), s541u numeric(2,0), s541v numeric(2,0),
      s541w numeric(2,0), s541x numeric(2,0), s541y numeric(2,0)
RECH5_All (reader CSV_3)
    attributes: FileCode char(7), HHID char(7), HA0 number(3,0), HA1 number(3,0), HA2 number(5,0), HA3 number(5,0), HA4 number(5,0), HA5 number(5,0), HA6 number(6,0), HA11 number(5,0), HA12 number(6,0), HA12A number(6,0), HA12B number(6,0), HA13 number(2,0), HA32 number(5,0), HA33 number(2,0), HA35 char(1), HA40 number(5,0), HA41 number(5,0), HA50 char(1), HA51 char(1), HA52 number(2,0), HA53 number(4,0), HA54 number(2,0), HA55 number(2,0), HA56 number(4,0), HA57 number(2,0), HA58 char(1), HA60 char(1), HA61 char(1),
      HA62 char(1), HA63 char(1), HA64 char(1), HA65 number(2,0), HA66 number(2,0), HA67 number(3,0), HA68 number(2,0), HA69 char(1), HA70 char(1)
    -> RECH5_All (writer POSTGRES_1)
RECH5_All (writer POSTGRES_1)
    attributes: filecode char(7), hhid char(7), ha0 numeric(3,0), ha1 numeric(3,0), ha2 numeric(5,0), ha3 numeric(5,0), ha4 numeric(5,0), ha5 numeric(5,0), ha6 numeric(6,0), ha11 numeric(5,0), ha12 numeric(6,0), ha12a numeric(6,0), ha12b numeric(6,0), ha13 numeric(2,0), ha32 numeric(5,0), ha33 numeric(2,0), ha35 char(1), ha40 numeric(5,0), ha41 numeric(5,0), ha50 char(1), ha51 char(1), ha52 numeric(2,0), ha53 numeric(4,0), ha54 numeric(2,0), ha55 numeric(2,0), ha56 numeric(4,0), ha57 numeric(2,0), ha58 char(1), ha60 char(1), ha61 char(1),
      ha62 char(1), ha63 char(1), ha64 char(1), ha65 numeric(2,0), ha66 numeric(2,0), ha67 numeric(3,0), ha68 numeric(2,0), ha69 char(1), ha70 char(1)
REC31_All (reader CSV_3)
    attributes: FileCode char(7), CASEID char(10), V301 char(1), V302 char(1), V302A number(2,0), REC31_GROUP number(2,0), V304A char(1), V304 char(1), V305 char(1), V307 number(2,0)
    -> REC31_All (writer POSTGRES_1)
REC31_All (writer POSTGRES_1)
    attributes: filecode char(7), caseid char(10), v301 char(1), v302 char(1), v302a numeric(2,0), rec31_group numeric(2,0), v304a char(1), v304 char(1), v305 char(1), v307 numeric(2,0)
REC84_All (reader CSV_3)
    attributes: FileCode char(7), CASEID char(9), MMC1 number(3,0), MMC2 number(3,0), MMC3 char(1), REC84_GROUP char(1), MMC4 char(1), MMC5 number(3,0)
    -> REC84_All (writer POSTGRES_1)
REC84_All (writer POSTGRES_1)
    attributes: filecode char(7), caseid char(9), mmc1 numeric(3,0), mmc2 numeric(3,0), mmc3 char(1), rec84_group char(1), mmc4 char(1), mmc5 numeric(3,0)
REC99_All (reader CSV_3)
    attributes: FileCode char(7), CASEID char(9), IDX99 number(2,0), SH2 number(2,0), SH2D number(3,0), SH2M number(3,0), SH2Y number(5,0), SH3 number(2,0), SH3D number(3,0), SH3M number(3,0), SH3Y number(5,0), SH4 number(2,0), SH4D number(3,0), SH4M number(3,0), SH4Y number(5,0), SH5 number(2,0), SH5D number(3,0), SH5M number(3,0), SH5Y number(5,0), SH6 number(2,0), SH6D number(3,0), SH6M number(3,0), SH6Y number(5,0), SH7 number(2,0), SH7D number(3,0), SH7M number(3,0), SH7Y number(5,0), SH8 number(2,0), SH8D number(3,0), SH8M number(3,0),
      SH8Y number(5,0), SH9 number(2,0), SH9D number(3,0), SH9M number(3,0), SH9Y number(5,0), SH0 number(2,0), SH0D number(3,0), SH0M number(3,0), SH0Y number(5,0), SH33 number(2,0), SH33D number(3,0), SH33M number(3,0), SH33Y number(5,0), SHP4 number(2,0), SHP4D number(3,0), SHP4M number(3,0), SHP4Y number(5,0), SHD4 number(2,0), SHD4D number(3,0), SHD4M number(3,0), SHD4Y number(5,0), SHH1 number(2,0), SHH1D number(3,0), SHH1M number(3,0), SHH1Y number(5,0), SHH2 number(2,0), SHH2D number(3,0), SHH2M number(3,0), SHH2Y number(5,0), SHH3 number(2,0),
      SHH3D number(3,0), SHH3M number(3,0), SHH3Y number(5,0), SHT1 number(2,0), SHT1D number(3,0), SHT1M number(3,0), SHT1Y number(5,0), SHT2 number(2,0), SHT2D number(3,0), SHT2M number(3,0), SHT2Y number(5,0), SHT3 number(2,0), SHT3D number(3,0), SHT3M number(3,0), SHT3Y number(5,0)
    -> REC99_All (writer POSTGRES_1)
REC99_All (writer POSTGRES_1)
    attributes: filecode char(7), caseid char(9), idx99 numeric(2,0), sh2 numeric(2,0), sh2d numeric(3,0), sh2m numeric(3,0), sh2y numeric(5,0), sh3 numeric(2,0), sh3d numeric(3,0), sh3m numeric(3,0), sh3y numeric(5,0), sh4 numeric(2,0), sh4d numeric(3,0), sh4m numeric(3,0), sh4y numeric(5,0), sh5 numeric(2,0), sh5d numeric(3,0), sh5m numeric(3,0), sh5y numeric(5,0), sh6 numeric(2,0), sh6d numeric(3,0), sh6m numeric(3,0), sh6y numeric(5,0), sh7 numeric(2,0), sh7d numeric(3,0), sh7m numeric(3,0), sh7y numeric(5,0), sh8 numeric(2,0), sh8d numeric(3,0), sh8m numeric(3,0),
      sh8y numeric(5,0), sh9 numeric(2,0), sh9d numeric(3,0), sh9m numeric(3,0), sh9y numeric(5,0), sh0 numeric(2,0), sh0d numeric(3,0), sh0m numeric(3,0), sh0y numeric(5,0), sh33 numeric(2,0), sh33d numeric(3,0), sh33m numeric(3,0), sh33y numeric(5,0), shp4 numeric(2,0), shp4d numeric(3,0), shp4m numeric(3,0), shp4y numeric(5,0), shd4 numeric(2,0), shd4d numeric(3,0), shd4m numeric(3,0), shd4y numeric(5,0), shh1 numeric(2,0), shh1d numeric(3,0), shh1m numeric(3,0), shh1y numeric(5,0), shh2 numeric(2,0), shh2d numeric(3,0), shh2m numeric(3,0), shh2y numeric(5,0), shh3 numeric(2,0),
      shh3d numeric(3,0), shh3m numeric(3,0), shh3y numeric(5,0), sht1 numeric(2,0), sht1d numeric(3,0), sht1m numeric(3,0), sht1y numeric(5,0), sht2 numeric(2,0), sht2d numeric(3,0), sht2m numeric(3,0), sht2y numeric(5,0), sht3 numeric(2,0), sht3d numeric(3,0), sht3m numeric(3,0), sht3y numeric(5,0)
RECHDP2_All (reader CSV_3)
    attributes: FileCode char(7), HHID char(6), HDPIDX2 number(2,0), SH197B number(3,0), SH197C number(2,0), SH197D number(2,0), SH197E number(2,0)
    -> RECHDP2_All (writer POSTGRES_1)
RECHDP2_All (writer POSTGRES_1)
    attributes: filecode char(7), hhid char(6), hdpidx2 numeric(2,0), sh197b numeric(3,0), sh197c numeric(2,0), sh197d numeric(2,0), sh197e numeric(2,0)
RECHML2_All (reader CSV_3)
    attributes: FileCode char(7), HHID char(6), HMLIDX2 number(2,0), SH133A number(3,0), SH133B number(2,0), SH133C number(2,0), SHMLA number(3,0), SHMLB number(3,0), SHMLC number(3,0), SHMLD number(3,0)
    -> RECHML2_All (writer POSTGRES_1)
RECHML2_All (writer POSTGRES_1)
    attributes: filecode char(7), hhid char(6), hmlidx2 numeric(2,0), sh133a numeric(3,0), sh133b numeric(2,0), sh133c numeric(2,0), shmla numeric(3,0), shmlb numeric(3,0), shmlc numeric(3,0), shmld numeric(3,0)
RECH0_All (reader CSV_3)
    attributes: FileCode char(7), HHID char(7), HV000 char(4), HV001 number(4,0), HV002 number(4,0), HV003 number(3,0), HV004 number(4,0), HV005 number(8,0), HV006 number(3,0), HV007 number(5,0), HV008 number(5,0), HV009 number(3,0), HV010 number(2,0), HV011 number(2,0), HV012 number(3,0), HV013 number(3,0), HV014 number(2,0), HV015 number(2,0), HV016 number(3,0), HV017 number(2,0), HV018 number(4,0), HV019 number(2,0), HV020 number(2,0), HV021 number(4,0), HV022 number(3,0), HV023 number(3,0), HV024 number(2,0), HV025 number(2,0), HV026 number(2,0), HV027 number(2,0),
      HV028 number(8,0), HV030 number(3,0), HV031 number(4,0), HV032 number(2,0), HV035 number(2,0), HV040 number(4,0), HV041 number(3,0), HV042 number(2,0), HV044 char(1)
    -> RECH0_All (writer POSTGRES_1)
RECH0_All (writer POSTGRES_1)
    attributes: filecode char(7), hhid char(7), hv000 char(4), hv001 numeric(4,0), hv002 numeric(4,0), hv003 numeric(3,0), hv004 numeric(4,0), hv005 numeric(8,0), hv006 numeric(3,0), hv007 numeric(5,0), hv008 numeric(5,0), hv009 numeric(3,0), hv010 numeric(2,0), hv011 numeric(2,0), hv012 numeric(3,0), hv013 numeric(3,0), hv014 numeric(2,0), hv015 numeric(2,0), hv016 numeric(3,0), hv017 numeric(2,0), hv018 numeric(4,0), hv019 numeric(2,0), hv020 numeric(2,0), hv021 numeric(4,0), hv022 numeric(3,0), hv023 numeric(3,0), hv024 numeric(2,0), hv025 numeric(2,0), hv026 numeric(2,0), hv027 numeric(2,0),
      hv028 numeric(8,0), hv030 numeric(3,0), hv031 numeric(4,0), hv032 numeric(2,0), hv035 numeric(2,0), hv040 numeric(4,0), hv041 numeric(3,0), hv042 numeric(2,0), hv044 char(1)
RECH9_All (reader CSV_3)
    attributes: FileCode char(7), HHID number(9,0), SHIDX9 number(2,0), SH78O number(3,0), SH79 number(3,0), SH80 number(4,0), SH81 number(3,0), SH82 number(2,0), SH83 number(2,0)
    -> RECH9_All (writer POSTGRES_1)
RECH9_All (writer POSTGRES_1)
    attributes: filecode char(7), hhid numeric(9,0), shidx9 numeric(2,0), sh78o numeric(3,0), sh79 numeric(3,0), sh80 numeric(4,0), sh81 numeric(3,0), sh82 numeric(2,0), sh83 numeric(2,0)
REC41_All (reader CSV_3)
    attributes: FileCode char(7), CASEID char(10), MIDX number(2,0), M1 number(2,0), M1A number(2,0), M1B char(1), M1C char(1), M1D number(3,0), M1E number(5,0), M2A number(2,0), M2B number(2,0), M2C number(2,0), M2D number(2,0), M2E number(2,0), M2F number(2,0), M2G number(2,0), M2H number(2,0), M2I number(2,0), M2J char(1), M2K number(2,0), M2L number(2,0), M2M number(2,0), M2N number(2,0), M3A number(2,0), M3B number(2,0), M3C number(2,0), M3D number(2,0), M3E number(2,0), M3F number(2,0), M3G number(2,0),
      M3H number(2,0), M3I number(2,0), M3J number(2,0), M3K number(2,0), M3L number(2,0), M3M number(2,0), M3N number(2,0), M4 number(3,0), M5 number(3,0), M6 number(3,0), M7 number(3,0), M8 number(3,0), M9 number(3,0), M10 number(2,0), M11 number(4,0), M13 number(3,0), M14 number(3,0), M15 number(3,0), M17 number(2,0), M18 number(2,0), M19 number(5,0), M19A number(2,0), M27 number(2,0), M28 number(2,0), M29 number(2,0), M34 number(4,0), M35 char(1), M36 char(1), M38 number(2,0), M39A number(2,0),
      M39 number(2,0), M42A char(1), M42B char(1), M42C number(2,0), M42D number(2,0), M42E number(2,0), M43 number(2,0), M44 char(1), M45 number(2,0), M46 number(4,0), M47 char(1), M48 char(1), M49A number(2,0), M49B number(2,0), M49C char(1), M49D char(1), M49E char(1), M49F char(1), M49G char(1), M49X number(2,0), M49Z number(2,0), M49Y number(2,0), M50 number(2,0), M51 number(4,0), M52 number(3,0), M54 number(2,0), M55A number(2,0), M55B number(2,0), M55C number(2,0), M55D number(2,0),
      M55E number(2,0), M55F number(2,0), M55G number(2,0), M55H number(2,0), M55I number(2,0), M55J number(2,0), M55K number(2,0), M55L char(1), M55M char(1), M55N char(1), M55O char(1), M55X number(2,0), M55Z number(2,0), M57A number(2,0), M57B number(2,0), M57C char(1), M57D char(1), M57E number(2,0), M57F number(2,0), M57G number(2,0), M57H number(2,0), M57I number(2,0), M57J number(2,0), M57K number(2,0), M57L number(2,0), M57M number(2,0), M57N number(2,0), M57O number(2,0), M57P number(2,0), M57Q number(2,0),
      M57R number(2,0), M57S number(2,0), M57T number(2,0), M57U char(1), M57V char(1), M57X number(2,0), M60 number(2,0), M61 number(4,0), M62 number(2,0), M65A char(1), M65B char(1), M65C char(1), M65D char(1), M65E char(1), M65F char(1), M65G char(1), M65H char(1), M65I char(1), M65J char(1), M65K char(1), M65L char(1), M65X char(1), M66 number(2,0), M70 number(2,0), M71 number(4,0), M72 number(3,0), M73 number(3,0)
    -> REC41_All (writer POSTGRES_1)
REC41_All (writer POSTGRES_1)
    attributes: filecode char(7), caseid char(10), midx numeric(2,0), m1 numeric(2,0), m1a numeric(2,0), m1b char(1), m1c char(1), m1d numeric(3,0), m1e numeric(5,0), m2a numeric(2,0), m2b numeric(2,0), m2c numeric(2,0), m2d numeric(2,0), m2e numeric(2,0), m2f numeric(2,0), m2g numeric(2,0), m2h numeric(2,0), m2i numeric(2,0), m2j char(1), m2k numeric(2,0), m2l numeric(2,0), m2m numeric(2,0), m2n numeric(2,0), m3a numeric(2,0), m3b numeric(2,0), m3c numeric(2,0), m3d numeric(2,0), m3e numeric(2,0), m3f numeric(2,0), m3g numeric(2,0),
      m3h numeric(2,0), m3i numeric(2,0), m3j numeric(2,0), m3k numeric(2,0), m3l numeric(2,0), m3m numeric(2,0), m3n numeric(2,0), m4 numeric(3,0), m5 numeric(3,0), m6 numeric(3,0), m7 numeric(3,0), m8 numeric(3,0), m9 numeric(3,0), m10 numeric(2,0), m11 numeric(4,0), m13 numeric(3,0), m14 numeric(3,0), m15 numeric(3,0), m17 numeric(2,0), m18 numeric(2,0), m19 numeric(5,0), m19a numeric(2,0), m27 numeric(2,0), m28 numeric(2,0), m29 numeric(2,0), m34 numeric(4,0), m35 char(1), m36 char(1), m38 numeric(2,0), m39a numeric(2,0),
      m39 numeric(2,0), m42a char(1), m42b char(1), m42c numeric(2,0), m42d numeric(2,0), m42e numeric(2,0), m43 numeric(2,0), m44 char(1), m45 numeric(2,0), m46 numeric(4,0), m47 char(1), m48 char(1), m49a numeric(2,0), m49b numeric(2,0), m49c char(1), m49d char(1), m49e char(1), m49f char(1), m49g char(1), m49x numeric(2,0), m49z numeric(2,0), m49y numeric(2,0), m50 numeric(2,0), m51 numeric(4,0), m52 numeric(3,0), m54 numeric(2,0), m55a numeric(2,0), m55b numeric(2,0), m55c numeric(2,0), m55d numeric(2,0),
      m55e numeric(2,0), m55f numeric(2,0), m55g numeric(2,0), m55h numeric(2,0), m55i numeric(2,0), m55j numeric(2,0), m55k numeric(2,0), m55l char(1), m55m char(1), m55n char(1), m55o char(1), m55x numeric(2,0), m55z numeric(2,0), m57a numeric(2,0), m57b numeric(2,0), m57c char(1), m57d char(1), m57e numeric(2,0), m57f numeric(2,0), m57g numeric(2,0), m57h numeric(2,0), m57i numeric(2,0), m57j numeric(2,0), m57k numeric(2,0), m57l numeric(2,0), m57m numeric(2,0), m57n numeric(2,0), m57o numeric(2,0), m57p numeric(2,0), m57q numeric(2,0),
      m57r numeric(2,0), m57s numeric(2,0), m57t numeric(2,0), m57u char(1), m57v char(1), m57x numeric(2,0), m60 numeric(2,0), m61 numeric(4,0), m62 numeric(2,0), m65a char(1), m65b char(1), m65c char(1), m65d char(1), m65e char(1), m65f char(1), m65g char(1), m65h char(1), m65i char(1), m65j char(1), m65k char(1), m65l char(1), m65x char(1), m66 numeric(2,0), m70 numeric(2,0), m71 numeric(4,0), m72 numeric(3,0), m73 numeric(3,0)
RECDV_All (reader CSV_3)
    attributes: FileCode char(7), CASEID char(9), D005 number(8,0), D101A number(2,0), D101B number(2,0), D101C number(2,0), D101D number(2,0), D101E number(2,0), D101F number(2,0), D101G number(2,0), D101H char(1), D101I char(1), D101J char(1), D102 number(2,0), D103A number(2,0), D103B number(2,0), D103C char(1), D103D char(1), D103E char(1), D103F char(1), D104 number(2,0), D105A number(2,0), D105B number(2,0), D105C number(2,0), D105D number(2,0), D105E number(2,0), D105F number(2,0), D105G number(2,0), D105H number(2,0), D105I number(2,0),
      D105J char(1), D105K char(1), D105L char(1), D105M char(1), D105N char(1), D106 number(2,0), D107 number(2,0), D108 number(2,0), D109 number(3,0), D110A number(2,0), D110B number(2,0), D110C number(2,0), D110D char(1), D110E char(1), D110F char(1), D110G char(1), D110H char(1), D111 number(2,0), D112 number(2,0), D112A number(2,0), D113 number(2,0), D114 number(2,0), D115B number(2,0), D115C number(2,0), D115D number(2,0), D115E number(2,0), D115F number(2,0), D115G number(2,0), D115H char(1), D115I char(1),
      D115J number(2,0), D115K number(2,0), D115L number(2,0), D115M number(2,0), D115N number(2,0), D115O number(2,0), D115P number(2,0), D115Q number(2,0), D115R number(2,0), D115S number(2,0), D115T number(2,0), D115U char(1), D115V number(2,0), D115W number(2,0), D115X number(2,0), D115Y number(2,0), D115XA number(2,0), D115XB char(1), D115XC char(1), D115XD char(1), D115XE char(1), D115XF char(1), D115XG char(1), D115XH char(1), D115XI char(1), D115XJ char(1), D115XK char(1), D116 number(3,0), D117A number(2,0), D118A char(1),
      D118B number(2,0), D118C number(2,0), D118D number(2,0), D118E number(2,0), D118F number(2,0), D118G number(2,0), D118H char(1), D118I char(1), D118J number(2,0), D118K number(2,0), D118L number(2,0), D118M number(2,0), D118N number(2,0), D118O number(2,0), D118P number(2,0), D118Q number(2,0), D118R number(2,0), D118S number(2,0), D118T number(2,0), D118U char(1), D118V number(2,0), D118W number(2,0), D118X number(2,0), D118Y number(2,0), D118XA number(2,0), D118XB char(1), D118XC char(1), D118XD char(1), D118XE char(1), D118XF char(1),
      D118XG char(1), D118XH char(1), D118XI char(1), D118XJ char(1), D118XK char(1), D119A char(1), D119B number(2,0), D119C number(2,0), D119D number(2,0), D119E number(2,0), D119F number(2,0), D119G number(2,0), D119H char(1), D119I char(1), D119J number(2,0), D119K number(2,0), D119L number(2,0), D119M number(2,0), D119N number(2,0), D119O number(2,0), D119P number(2,0), D119Q number(2,0), D119R number(2,0), D119S number(2,0), D119T number(2,0), D119U char(1), D119V number(2,0), D119W number(2,0), D119X number(2,0), D119Y number(2,0),
      D119XA number(2,0), D119XB char(1), D119XC char(1), D119XD char(1), D119XE char(1), D119XF char(1), D119XG char(1), D119XH char(1), D119XI char(1), D119XJ char(1), D119XK char(1), D120 number(3,0), D121 number(2,0), D122A number(2,0), D122B number(2,0), D122C number(2,0), D123 char(1), D124 char(1), D125 char(1), D126 char(1), D127 char(1), D128 char(1), D129 char(1), D130A char(1), D130B char(1), D100A number(2,0), D100B number(2,0), D100C number(2,0), D100D number(2,0), D112N char(1),
      D117 char(1), D121A number(2,0), D1310A number(2,0), D1310B number(3,0)
    -> RECDV_All (writer POSTGRES_1)
RECDV_All (writer POSTGRES_1)
    attributes: filecode char(7), caseid char(9), d005 numeric(8,0), d101a numeric(2,0), d101b numeric(2,0), d101c numeric(2,0), d101d numeric(2,0), d101e numeric(2,0), d101f numeric(2,0), d101g numeric(2,0), d101h char(1), d101i char(1), d101j char(1), d102 numeric(2,0), d103a numeric(2,0), d103b numeric(2,0), d103c char(1), d103d char(1), d103e char(1), d103f char(1), d104 numeric(2,0), d105a numeric(2,0), d105b numeric(2,0), d105c numeric(2,0), d105d numeric(2,0), d105e numeric(2,0), d105f numeric(2,0), d105g numeric(2,0), d105h numeric(2,0), d105i numeric(2,0),
      d105j char(1), d105k char(1), d105l char(1), d105m char(1), d105n char(1), d106 numeric(2,0), d107 numeric(2,0), d108 numeric(2,0), d109 numeric(3,0), d110a numeric(2,0), d110b numeric(2,0), d110c numeric(2,0), d110d char(1), d110e char(1), d110f char(1), d110g char(1), d110h char(1), d111 numeric(2,0), d112 numeric(2,0), d112a numeric(2,0), d113 numeric(2,0), d114 numeric(2,0), d115b numeric(2,0), d115c numeric(2,0), d115d numeric(2,0), d115e numeric(2,0), d115f numeric(2,0), d115g numeric(2,0), d115h char(1), d115i char(1),
      d115j numeric(2,0), d115k numeric(2,0), d115l numeric(2,0), d115m numeric(2,0), d115n numeric(2,0), d115o numeric(2,0), d115p numeric(2,0), d115q numeric(2,0), d115r numeric(2,0), d115s numeric(2,0), d115t numeric(2,0), d115u char(1), d115v numeric(2,0), d115w numeric(2,0), d115x numeric(2,0), d115y numeric(2,0), d115xa numeric(2,0), d115xb char(1), d115xc char(1), d115xd char(1), d115xe char(1), d115xf char(1), d115xg char(1), d115xh char(1), d115xi char(1), d115xj char(1), d115xk char(1), d116 numeric(3,0), d117a numeric(2,0), d118a char(1),
      d118b numeric(2,0), d118c numeric(2,0), d118d numeric(2,0), d118e numeric(2,0), d118f numeric(2,0), d118g numeric(2,0), d118h char(1), d118i char(1), d118j numeric(2,0), d118k numeric(2,0), d118l numeric(2,0), d118m numeric(2,0), d118n numeric(2,0), d118o numeric(2,0), d118p numeric(2,0), d118q numeric(2,0), d118r numeric(2,0), d118s numeric(2,0), d118t numeric(2,0), d118u char(1), d118v numeric(2,0), d118w numeric(2,0), d118x numeric(2,0), d118y numeric(2,0), d118xa numeric(2,0), d118xb char(1), d118xc char(1), d118xd char(1), d118xe char(1), d118xf char(1),
      d118xg char(1), d118xh char(1), d118xi char(1), d118xj char(1), d118xk char(1), d119a char(1), d119b numeric(2,0), d119c numeric(2,0), d119d numeric(2,0), d119e numeric(2,0), d119f numeric(2,0), d119g numeric(2,0), d119h char(1), d119i char(1), d119j numeric(2,0), d119k numeric(2,0), d119l numeric(2,0), d119m numeric(2,0), d119n numeric(2,0), d119o numeric(2,0), d119p numeric(2,0), d119q numeric(2,0), d119r numeric(2,0), d119s numeric(2,0), d119t numeric(2,0), d119u char(1), d119v numeric(2,0), d119w numeric(2,0), d119x numeric(2,0), d119y numeric(2,0),
      d119xa numeric(2,0), d119xb char(1), d119xc char(1), d119xd char(1), d119xe char(1), d119xf char(1), d119xg char(1), d119xh char(1), d119xi char(1), d119xj char(1), d119xk char(1), d120 numeric(3,0), d121 numeric(2,0), d122a numeric(2,0), d122b numeric(2,0), d122c numeric(2,0), d123 char(1), d124 char(1), d125 char(1), d126 char(1), d127 char(1), d128 char(1), d129 char(1), d130a char(1), d130b char(1), d100a numeric(2,0), d100b numeric(2,0), d100c numeric(2,0), d100d numeric(2,0), d112n char(1),
      d117 char(1), d121a numeric(2,0), d1310a numeric(2,0), d1310b numeric(3,0)
REC94_All (reader CSV_3)
    attributes: FileCode char(7), CASEID char(10), IDX94 number(2,0), S410J number(3,0), S433L number(3,0), S435C number(2,0), S435D number(2,0), S435E number(2,0), S435F number(2,0), S435GA number(2,0), S435GB number(2,0), S435GC number(2,0), S435GD number(2,0), S435GE number(2,0), S435GF number(2,0), S435GG number(2,0), S435GH number(2,0), S435GI number(2,0), S435GJ number(2,0), S435GK number(2,0), S435GL number(2,0), S435GM number(2,0), S435GN number(2,0), S435GX number(2,0), S435GZ number(2,0), S435H number(4,0), S435I number(2,0), S435J number(2,0), S439A number(3,0)
    -> REC94_All (writer POSTGRES_1)
REC94_All (writer POSTGRES_1)
    attributes: filecode char(7), caseid char(10), idx94 numeric(2,0), s410j numeric(3,0), s433l numeric(3,0), s435c numeric(2,0), s435d numeric(2,0), s435e numeric(2,0), s435f numeric(2,0), s435ga numeric(2,0), s435gb numeric(2,0), s435gc numeric(2,0), s435gd numeric(2,0), s435ge numeric(2,0), s435gf numeric(2,0), s435gg numeric(2,0), s435gh numeric(2,0), s435gi numeric(2,0), s435gj numeric(2,0), s435gk numeric(2,0), s435gl numeric(2,0), s435gm numeric(2,0), s435gn numeric(2,0), s435gx numeric(2,0), s435gz numeric(2,0), s435h numeric(4,0), s435i numeric(2,0), s435j numeric(2,0), s439a numeric(3,0)
RECH4_All (reader CSV_3)
    attributes: FileCode char(7), HHID char(6), IDXH4 number(3,0), SH08 number(2,0), SH13 number(2,0), SH18 number(2,0), SH19 number(2,0), SH20 number(2,0), SH21 number(2,0), SH22 number(2,0)
    -> RECH4_All (writer POSTGRES_1)
RECH4_All (writer POSTGRES_1)
    attributes: filecode char(7), hhid char(6), idxh4 numeric(3,0), sh08 numeric(2,0), sh13 numeric(2,0), sh18 numeric(2,0), sh19 numeric(2,0), sh20 numeric(2,0), sh21 numeric(2,0), sh22 numeric(2,0)
REC83_All (reader CSV_3)
    attributes: FileCode char(7), CASEID char(9), MMIDX number(3,0), MM1 number(2,0), MM2 number(2,0), MM3 number(3,0), MM4 number(5,0), MM5 char(1), MM6 number(3,0), MM7 number(3,0), MM8 number(5,0), MM9 number(3,0), MM10 char(1), MM11 char(1), MM12 char(1), MM13 char(1), MM14 number(3,0), MM15 char(1)
    -> REC83_All (writer POSTGRES_1)
REC83_All (writer POSTGRES_1)
    attributes: filecode char(7), caseid char(9), mmidx numeric(3,0), mm1 numeric(2,0), mm2 numeric(2,0), mm3 numeric(3,0), mm4 numeric(5,0), mm5 char(1), mm6 numeric(3,0), mm7 numeric(3,0), mm8 numeric(5,0), mm9 numeric(3,0), mm10 char(1), mm11 char(1), mm12 char(1), mm13 char(1), mm14 numeric(3,0), mm15 char(1)
RECHDP_All (reader CSV_3)
    attributes: FileCode char(7), HHID char(7), HDPIDX number(3,0), HD100 number(3,0), HD101 number(4,0)
    -> RECHDP_All (writer POSTGRES_1)
RECHDP_All (writer POSTGRES_1)
    attributes: filecode char(7), hhid char(7), hdpidx numeric(3,0), hd100 numeric(3,0), hd101 numeric(4,0)
RECHMH_All (reader CSV_3)
    attributes: FileCode char(7), HHID char(6), HMHIDX number(3,0), HML12 number(2,0), HML13 number(2,0), HML14 number(2,0), HML15 char(1), HML16 number(3,0), HML16A number(3,0), HML17 number(2,0), HML18 number(2,0), HML19 number(2,0), HML20 number(2,0), HML30 number(3,0), HML31 number(2,0), HML32 number(2,0), HML32A char(1), HML32B char(1), HML32C char(1), HML32D char(1), HML32E char(1), HML32F char(1), HML32G char(1), HML33 char(1), HML34 char(6), HML35 number(2,0)
    -> RECHMH_All (writer POSTGRES_1)
RECHMH_All (writer POSTGRES_1)
    attributes: filecode char(7), hhid char(6), hmhidx numeric(3,0), hml12 numeric(2,0), hml13 numeric(2,0), hml14 numeric(2,0), hml15 char(1), hml16 numeric(3,0), hml16a numeric(3,0), hml17 numeric(2,0), hml18 numeric(2,0), hml19 numeric(2,0), hml20 numeric(2,0), hml30 numeric(3,0), hml31 numeric(2,0), hml32 numeric(2,0), hml32a char(1), hml32b char(1), hml32c char(1), hml32d char(1), hml32e char(1), hml32f char(1), hml32g char(1), hml33 char(1), hml34 char(6), hml35 numeric(2,0)
REC51_All (reader CSV_3)
    attributes: FileCode char(7), CASEID char(10), V501 number(2,0), V502 number(2,0), V503 number(2,0), V504 number(2,0), V505 char(1), V506 char(1), V507 number(3,0), V508 number(5,0), V509 number(5,0), V510 number(2,0), V511 number(3,0), V512 number(3,0), V513 number(2,0), V525 number(3,0), V527 number(4,0), V528 number(3,0), V529 number(4,0), V530 number(2,0), V531 number(3,0), V532 number(2,0), V535 number(2,0), V536 number(2,0), V537 number(3,0), V538 char(1), V539 char(1), V540 char(1), V541 char(1)
    -> REC51_All (writer POSTGRES_1)
REC51_All (writer POSTGRES_1)
    attributes: filecode char(7), caseid char(10), v501 numeric(2,0), v502 numeric(2,0), v503 numeric(2,0), v504 numeric(2,0), v505 char(1), v506 char(1), v507 numeric(3,0), v508 numeric(5,0), v509 numeric(5,0), v510 numeric(2,0), v511 numeric(3,0), v512 numeric(3,0), v513 numeric(2,0), v525 numeric(3,0), v527 numeric(4,0), v528 numeric(3,0), v529 numeric(4,0), v530 numeric(2,0), v531 numeric(3,0), v532 numeric(2,0), v535 numeric(2,0), v536 numeric(2,0), v537 numeric(3,0), v538 char(1), v539 char(1), v540 char(1), v541 char(1)
REC98_All (reader CSV_3)
    attributes: FileCode char(7), CASEID char(11), IDX98 number(2,0), S570 number(3,0), S571 number(3,0), S572 number(3,0), S573A number(2,0), S573B number(9,0), S573C number(3,0), S573D number(3,0), S573E number(5,0), S575 number(9,0), S576A number(3,0), S576B number(3,0), S576C number(5,0), S576D number(9,0), S576E number(3,0), S576F number(3,0), S576G number(5,0), S576H number(9,0), S576I number(3,0), S576J number(3,0), S577A number(5,0), S577B number(9,0), S577C number(3,0), S577D number(3,0), S577E number(5,0), S577F number(9,0), S577G number(3,0), S577G1 number(3,0),
      S577G2 number(5,0), S577H number(9,0), S577I number(3,0), S577J number(3,0), S577K number(5,0), S577L number(9,0), S577M number(3,0), S577N number(3,0), S577O number(5,0), S577P number(9,0), S577Q number(3,0), S577R number(3,0), S578A number(5,0), S578B number(9,0), S578C number(3,0), S578D number(3,0), S578E number(5,0), S578F number(9,0), S578G number(3,0), S578H number(3,0), S578I number(5,0), S578J number(9,0), S578K number(3,0), S578L number(3,0), S578M number(5,0), S578N number(9,0), S578O number(3,0), S578P number(3,0), S578P1 number(5,0), S578P2 number(9,0),
      S578Q number(3,0), S578R number(3,0), S578S number(5,0), S578T number(9,0), S578U number(3,0), S578V number(3,0), S578W number(5,0), S578X number(9,0), S578Y number(3,0), S579A number(3,0), S579B number(5,0), S579C number(9,0), S579D number(3,0), S579E number(3,0), S579F number(5,0), S579G number(9,0), S580 number(3,0), S581A number(3,0), S581B number(5,0), S581C number(2,0), S581D number(2,0), S581E number(2,0), S581F number(2,0), S581G number(2,0), S581H number(2,0), S581I number(2,0), S581J number(2,0), S581X number(2,0), S582 number(2,0), S583 number(3,0),
      S583B number(3,0), S584 number(3,0), S584B number(3,0), S585 number(2,0), S586 number(2,0), S587 number(3,0), S588 number(2,0), S589 number(3,0), S591 number(3,0)
    -> REC98_All (writer POSTGRES_1)
REC98_All (writer POSTGRES_1)
    attributes: filecode char(7), caseid char(11), idx98 numeric(2,0), s570 numeric(3,0), s571 numeric(3,0), s572 numeric(3,0), s573a numeric(2,0), s573b numeric(9,0), s573c numeric(3,0), s573d numeric(3,0), s573e numeric(5,0), s575 numeric(9,0), s576a numeric(3,0), s576b numeric(3,0), s576c numeric(5,0), s576d numeric(9,0), s576e numeric(3,0), s576f numeric(3,0), s576g numeric(5,0), s576h numeric(9,0), s576i numeric(3,0), s576j numeric(3,0), s577a numeric(5,0), s577b numeric(9,0), s577c numeric(3,0), s577d numeric(3,0), s577e numeric(5,0), s577f numeric(9,0), s577g numeric(3,0), s577g1 numeric(3,0),
      s577g2 numeric(5,0), s577h numeric(9,0), s577i numeric(3,0), s577j numeric(3,0), s577k numeric(5,0), s577l numeric(9,0), s577m numeric(3,0), s577n numeric(3,0), s577o numeric(5,0), s577p numeric(9,0), s577q numeric(3,0), s577r numeric(3,0), s578a numeric(5,0), s578b numeric(9,0), s578c numeric(3,0), s578d numeric(3,0), s578e numeric(5,0), s578f numeric(9,0), s578g numeric(3,0), s578h numeric(3,0), s578i numeric(5,0), s578j numeric(9,0), s578k numeric(3,0), s578l numeric(3,0), s578m numeric(5,0), s578n numeric(9,0), s578o numeric(3,0), s578p numeric(3,0), s578p1 numeric(5,0), s578p2 numeric(9,0),
      s578q numeric(3,0), s578r numeric(3,0), s578s numeric(5,0), s578t numeric(9,0), s578u numeric(3,0), s578v numeric(3,0), s578w numeric(5,0), s578x numeric(9,0), s578y numeric(3,0), s579a numeric(3,0), s579b numeric(5,0), s579c numeric(9,0), s579d numeric(3,0), s579e numeric(3,0), s579f numeric(5,0), s579g numeric(9,0), s580 numeric(3,0), s581a numeric(3,0), s581b numeric(5,0), s581c numeric(2,0), s581d numeric(2,0), s581e numeric(2,0), s581f numeric(2,0), s581g numeric(2,0), s581h numeric(2,0), s581i numeric(2,0), s581j numeric(2,0), s581x numeric(2,0), s582 numeric(2,0), s583 numeric(3,0),
      s583b numeric(3,0), s584 numeric(3,0), s584b numeric(3,0), s585 numeric(2,0), s586 numeric(2,0), s587 numeric(3,0), s588 numeric(2,0), s589 numeric(3,0), s591 numeric(3,0)
REC9A_All (reader CSV_3)
    attributes: FileCode char(7), CASEID char(9), IDX9A number(3,0), S1113 number(2,0)
    -> REC9A_All (writer POSTGRES_1)
REC9A_All (writer POSTGRES_1)
    attributes: filecode char(7), caseid char(9), idx9a numeric(3,0), s1113 numeric(2,0)
RECHG2_All (reader CSV_3)
    attributes: FileCode char(7), HHID char(7), SG101 number(3,0), SG103 number(3,0), SG104 number(2,0), SG105 number(2,0), SG106 number(2,0), SG107 number(2,0), SG108 number(3,0), SG109 number(2,0), SG110 number(4,0), SG111 number(3,0), SG112A number(7,0), SG112B number(2,0), SG113A number(6,0), SG113B number(6,0), SG113C number(6,0), SG113D number(6,0), SG114A number(7,0), SG114B number(7,0), SG115 number(2,0), SG116A number(3,0), SG116B number(3,0), SG116C number(3,0), SG116D number(3,0), SG117A number(7,0), SG117B number(2,0), SG118A number(7,0), SG118B number(2,0), SG119A number(7,0),
      SG119B number(2,0), SG120A number(6,0), SG120B number(2,0), SG121 number(2,0), SG122 number(2,0), SG123A number(2,0), SG123B number(2,0), SG123C number(2,0), SG123D number(2,0), SG123E number(2,0), SG123F number(2,0), SG123G number(2,0), SG123H number(2,0), SG123I number(2,0), SG123J number(2,0), SG123X number(2,0), SG124 number(2,0), SG125 number(2,0), SG126 number(7,0), SG127 number(3,0), SG128 number(2,0), SG129 number(2,0), SG201A number(2,0), SG201B number(2,0), SG201C number(2,0), SG201D number(2,0), SG201E number(2,0), SG201F number(2,0), SG201G number(2,0), SG201H number(2,0),
      SG201I number(2,0), SG201J number(2,0), SG201K number(2,0), SG201L number(2,0), SG201M number(2,0), SG201N number(2,0), SG201X number(2,0), SG202A number(2,0), SG202B number(2,0), SG202C number(2,0), SG202D number(2,0), SG202E number(2,0), SG202F number(2,0), SG202G number(2,0), SG202H number(2,0), SG202I number(2,0), SG202J number(2,0), SG202K number(2,0), SG202L number(2,0), SG202M number(2,0), SG202N char(1), SG202X number(2,0), SG203A number(2,0), SG203B number(3,0), SG204M number(3,0), SG204A number(5,0), SG205 number(3,0), SG206A number(2,0), SG206B number(6,0), SG207 number(3,0),
      SG207B number(2,0), SG208A number(2,0), SG208B number(7,0), SG209 number(2,0), SG210 number(2,0), SG211 number(2,0), SG213A number(2,0), SG213B number(7,0), SG214 number(2,0), SG215 number(2,0), SG216A number(2,0), SG216B number(2,0), SG216C number(2,0), SG216D number(2,0), SG216E number(2,0), SG216F number(2,0), SG216G number(2,0), SG216H number(2,0), SG216I number(2,0), SG216X number(2,0), SG216Z number(2,0), SG217A number(2,0), SG217B number(2,0), SG217C number(2,0), SG217D number(2,0), SG217E number(2,0), SG217F number(2,0), SG217G number(2,0), SG217H number(2,0), SG217I number(2,0),
      SG217X number(2,0), SG217Y number(2,0), SG217Z number(2,0), SG218 number(2,0), SG219A number(2,0), SG219B number(7,0), SG220 number(2,0), SG221 number(2,0), SG222A number(2,0), SG222B number(2,0), SG222C number(2,0), SG222D number(2,0), SG222E number(2,0), SG222F number(2,0), SG222G number(2,0), SG222H number(2,0), SG222I number(2,0), SG222J number(2,0), SG222K number(2,0), SG222X number(2,0), SG222Z number(2,0), SG223A number(2,0), SG223B number(2,0), SG223C number(2,0), SG223D number(2,0), SG223E number(2,0), SG223F number(2,0), SG223G number(2,0), SG223H number(2,0), SG223I number(2,0),
      SG223J number(2,0), SG223K number(2,0), SG223X number(2,0), SG223Y number(2,0), SG223Z number(2,0), SG224 number(2,0), SG225A number(2,0), SG225B number(7,0), SG226 number(2,0), SG227 number(6,0), SG228A number(2,0), SG228B number(2,0), SG228C number(2,0), SG228D number(2,0), SG228E number(2,0), SG228F number(2,0), SG228G number(2,0), SG228H number(2,0), SG228I number(2,0), SG228J number(2,0), SG228X number(2,0), SG228Y number(2,0), SG228Z number(2,0), SG229 number(3,0), SG230M number(3,0), SG230A number(5,0), SG231 number(3,0), SG232A number(2,0), SG232B number(6,0), SG233 number(2,0),
      SG234 number(2,0), SG235 number(2,0), SG237A number(2,0), SG237B number(6,0), SG238 number(2,0), SG239 number(2,0), SG240A number(2,0), SG240B number(2,0), SG240C number(2,0), SG240D number(2,0), SG240E number(2,0), SG240F number(2,0), SG240G number(2,0), SG240H number(2,0), SG240I number(2,0), SG240X number(2,0), SG240Z number(2,0), SG241A number(2,0), SG241B number(2,0), SG241C number(2,0), SG241D number(2,0), SG241E number(2,0), SG241F number(2,0), SG241G number(2,0), SG241H number(2,0), SG241I number(2,0), SG241X number(2,0), SG241Y number(2,0), SG241Z number(2,0), SG242 number(2,0),
      SG243A number(2,0), SG243B number(7,0), SG244 number(2,0), SG245 number(2,0), SG246A number(2,0), SG246B number(2,0), SG246C number(2,0), SG246D number(2,0), SG246E number(2,0), SG246X number(2,0), SG246Z number(2,0), SG247A number(2,0), SG247B number(2,0), SG247C number(2,0), SG247D number(2,0), SG247E number(2,0), SG247X number(2,0), SG247Y number(2,0), SG247Z number(2,0), SG248 number(2,0), SG249A number(2,0), SG249B number(7,0), SG250 number(2,0), SG251 number(6,0), SG252 number(2,0), SG253A number(4,0), SG253B number(4,0), SG253C number(4,0), SG253 number(4,0), SG254 number(3,0),
      SG255 number(3,0), SG256A number(2,0), SG256B number(6,0), SG257 number(3,0), SG258A number(2,0), SG258B number(7,0), SG259 number(2,0), SG260 number(2,0), SG261 number(2,0), SG262A number(2,0), SG262B number(6,0), SG263 number(2,0), SG264 number(2,0), SG265A number(2,0), SG265B number(2,0), SG265C number(2,0), SG265D number(2,0), SG265E number(2,0), SG265F number(2,0), SG265G number(2,0), SG265H number(2,0), SG265I number(2,0), SG265X number(2,0), SG265Z number(2,0), SG265AA number(2,0), SG265AB number(2,0), SG265AC number(2,0), SG265AD number(2,0), SG265AE number(2,0), SG265AF number(2,0),
      SG265AG number(2,0), SG265AH number(2,0), SG265AI number(2,0), SG265AX number(2,0), SG265AY number(2,0), SG265AZ number(2,0), SG265BB number(2,0), SG266A number(2,0), SG266B number(7,0), SG267 number(2,0), SG268 number(2,0), SG269A number(2,0), SG269B number(2,0), SG269C number(2,0), SG269D number(2,0), SG269E number(2,0), SG269F number(2,0), SG269G number(2,0), SG269H number(2,0), SG269I number(2,0), SG269J number(2,0), SG269K number(2,0), SG269X number(2,0), SG269Z number(2,0), SG270A number(2,0), SG270B number(2,0), SG270C number(2,0), SG270D number(2,0), SG270E number(2,0), SG270F number(2,0),
      SG270G number(2,0), SG270H number(2,0), SG270I number(2,0), SG270J number(2,0), SG270K number(2,0), SG270X number(2,0), SG270Y number(2,0), SG270Z number(2,0), SG271 number(2,0), SG272A number(2,0), SG272B number(7,0), SG273 number(2,0), SG274 number(6,0), SG275 number(2,0), SG276 number(4,0), SG277 number(2,0), SG278 number(2,0), SG279U number(2,0), SG279N number(2,0), SG280A number(2,0), SG280B number(7,0), SG281 number(2,0), SG282A number(2,0), SG282B number(2,0), SG282C number(2,0), SG283 number(6,0), SG284 number(2,0), SG285 number(2,0), SG286 number(6,0), SG287 number(2,0),
      SG288 number(2,0), SG289 number(7,0), SG290 number(2,0), SG291 number(3,0), SG292 number(6,0), SG292A number(7,0), SG301A number(2,0), SG301B number(2,0), SG301C number(2,0), SG301D number(2,0), SG301E number(2,0), SG301F number(2,0), SG301G number(2,0), SG301H number(2,0), SG301X number(2,0), SG302 number(2,0), SG303A number(2,0), SG303B number(2,0), SG303C number(2,0), SG304A number(2,0), SG304B number(2,0), SG304C number(2,0), SG304D number(2,0), SG304E number(2,0), SG304X number(2,0), SG305 number(3,0), SG306 number(2,0), SG307 number(2,0), SG308 number(2,0), SG309 number(2,0),
      SG310 number(2,0), SG311 number(3,0), SINGRESOO number(8,0), SINGRESOE number(7,0), SREGALIAP number(7,0), SBONIFICA number(7,0), SIFUENTE1 number(8,0), SIFUENTE2 number(7,0), SIFUENTE3 number(7,0), SIFUENTE4 number(6,0), SINGRESOTP number(8,0), SINGRESOIP number(2,0), SINGRESOIB number(3,0), SGASTOTI char(1), SINGRESOIPA number(2,0)
    -> RECHG2_All (writer POSTGRES_1)
RECHG2_All (writer POSTGRES_1)
    attributes: filecode char(7), hhid char(7), sg101 numeric(3,0), sg103 numeric(3,0), sg104 numeric(2,0), sg105 numeric(2,0), sg106 numeric(2,0), sg107 numeric(2,0), sg108 numeric(3,0), sg109 numeric(2,0), sg110 numeric(4,0), sg111 numeric(3,0), sg112a numeric(7,0), sg112b numeric(2,0), sg113a numeric(6,0), sg113b numeric(6,0), sg113c numeric(6,0), sg113d numeric(6,0), sg114a numeric(7,0), sg114b numeric(7,0), sg115 numeric(2,0), sg116a numeric(3,0), sg116b numeric(3,0), sg116c numeric(3,0), sg116d numeric(3,0), sg117a numeric(7,0), sg117b numeric(2,0), sg118a numeric(7,0), sg118b numeric(2,0), sg119a numeric(7,0),
      sg119b numeric(2,0), sg120a numeric(6,0), sg120b numeric(2,0), sg121 numeric(2,0), sg122 numeric(2,0), sg123a numeric(2,0), sg123b numeric(2,0), sg123c numeric(2,0), sg123d numeric(2,0), sg123e numeric(2,0), sg123f numeric(2,0), sg123g numeric(2,0), sg123h numeric(2,0), sg123i numeric(2,0), sg123j numeric(2,0), sg123x numeric(2,0), sg124 numeric(2,0), sg125 numeric(2,0), sg126 numeric(7,0), sg127 numeric(3,0), sg128 numeric(2,0), sg129 numeric(2,0), sg201a numeric(2,0), sg201b numeric(2,0), sg201c numeric(2,0), sg201d numeric(2,0), sg201e numeric(2,0), sg201f numeric(2,0), sg201g numeric(2,0), sg201h numeric(2,0),
      sg201i numeric(2,0), sg201j numeric(2,0), sg201k numeric(2,0), sg201l numeric(2,0), sg201m numeric(2,0), sg201n numeric(2,0), sg201x numeric(2,0), sg202a numeric(2,0), sg202b numeric(2,0), sg202c numeric(2,0), sg202d numeric(2,0), sg202e numeric(2,0), sg202f numeric(2,0), sg202g numeric(2,0), sg202h numeric(2,0), sg202i numeric(2,0), sg202j numeric(2,0), sg202k numeric(2,0), sg202l numeric(2,0), sg202m numeric(2,0), sg202n char(1), sg202x numeric(2,0), sg203a numeric(2,0), sg203b numeric(3,0), sg204m numeric(3,0), sg204a numeric(5,0), sg205 numeric(3,0), sg206a numeric(2,0), sg206b numeric(6,0), sg207 numeric(3,0),
      sg207b numeric(2,0), sg208a numeric(2,0), sg208b numeric(7,0), sg209 numeric(2,0), sg210 numeric(2,0), sg211 numeric(2,0), sg213a numeric(2,0), sg213b numeric(7,0), sg214 numeric(2,0), sg215 numeric(2,0), sg216a numeric(2,0), sg216b numeric(2,0), sg216c numeric(2,0), sg216d numeric(2,0), sg216e numeric(2,0), sg216f numeric(2,0), sg216g numeric(2,0), sg216h numeric(2,0), sg216i numeric(2,0), sg216x numeric(2,0), sg216z numeric(2,0), sg217a numeric(2,0), sg217b numeric(2,0), sg217c numeric(2,0), sg217d numeric(2,0), sg217e numeric(2,0), sg217f numeric(2,0), sg217g numeric(2,0), sg217h numeric(2,0), sg217i numeric(2,0),
      sg217x numeric(2,0), sg217y numeric(2,0), sg217z numeric(2,0), sg218 numeric(2,0), sg219a numeric(2,0), sg219b numeric(7,0), sg220 numeric(2,0), sg221 numeric(2,0), sg222a numeric(2,0), sg222b numeric(2,0), sg222c numeric(2,0), sg222d numeric(2,0), sg222e numeric(2,0), sg222f numeric(2,0), sg222g numeric(2,0), sg222h numeric(2,0), sg222i numeric(2,0), sg222j numeric(2,0), sg222k numeric(2,0), sg222x numeric(2,0), sg222z numeric(2,0), sg223a numeric(2,0), sg223b numeric(2,0), sg223c numeric(2,0), sg223d numeric(2,0), sg223e numeric(2,0), sg223f numeric(2,0), sg223g numeric(2,0), sg223h numeric(2,0), sg223i numeric(2,0),
      sg223j numeric(2,0), sg223k numeric(2,0), sg223x numeric(2,0), sg223y numeric(2,0), sg223z numeric(2,0), sg224 numeric(2,0), sg225a numeric(2,0), sg225b numeric(7,0), sg226 numeric(2,0), sg227 numeric(6,0), sg228a numeric(2,0), sg228b numeric(2,0), sg228c numeric(2,0), sg228d numeric(2,0), sg228e numeric(2,0), sg228f numeric(2,0), sg228g numeric(2,0), sg228h numeric(2,0), sg228i numeric(2,0), sg228j numeric(2,0), sg228x numeric(2,0), sg228y numeric(2,0), sg228z numeric(2,0), sg229 numeric(3,0), sg230m numeric(3,0), sg230a numeric(5,0), sg231 numeric(3,0), sg232a numeric(2,0), sg232b numeric(6,0), sg233 numeric(2,0),
      sg234 numeric(2,0), sg235 numeric(2,0), sg237a numeric(2,0), sg237b numeric(6,0), sg238 numeric(2,0), sg239 numeric(2,0), sg240a numeric(2,0), sg240b numeric(2,0), sg240c numeric(2,0), sg240d numeric(2,0), sg240e numeric(2,0), sg240f numeric(2,0), sg240g numeric(2,0), sg240h numeric(2,0), sg240i numeric(2,0), sg240x numeric(2,0), sg240z numeric(2,0), sg241a numeric(2,0), sg241b numeric(2,0), sg241c numeric(2,0), sg241d numeric(2,0), sg241e numeric(2,0), sg241f numeric(2,0), sg241g numeric(2,0), sg241h numeric(2,0), sg241i numeric(2,0), sg241x numeric(2,0), sg241y numeric(2,0), sg241z numeric(2,0), sg242 numeric(2,0),
      sg243a numeric(2,0), sg243b numeric(7,0), sg244 numeric(2,0), sg245 numeric(2,0), sg246a numeric(2,0), sg246b numeric(2,0), sg246c numeric(2,0), sg246d numeric(2,0), sg246e numeric(2,0), sg246x numeric(2,0), sg246z numeric(2,0), sg247a numeric(2,0), sg247b numeric(2,0), sg247c numeric(2,0), sg247d numeric(2,0), sg247e numeric(2,0), sg247x numeric(2,0), sg247y numeric(2,0), sg247z numeric(2,0), sg248 numeric(2,0), sg249a numeric(2,0), sg249b numeric(7,0), sg250 numeric(2,0), sg251 numeric(6,0), sg252 numeric(2,0), sg253a numeric(4,0), sg253b numeric(4,0), sg253c numeric(4,0), sg253 numeric(4,0), sg254 numeric(3,0),
      sg255 numeric(3,0), sg256a numeric(2,0), sg256b numeric(6,0), sg257 numeric(3,0), sg258a numeric(2,0), sg258b numeric(7,0), sg259 numeric(2,0), sg260 numeric(2,0), sg261 numeric(2,0), sg262a numeric(2,0), sg262b numeric(6,0), sg263 numeric(2,0), sg264 numeric(2,0), sg265a numeric(2,0), sg265b numeric(2,0), sg265c numeric(2,0), sg265d numeric(2,0), sg265e numeric(2,0), sg265f numeric(2,0), sg265g numeric(2,0), sg265h numeric(2,0), sg265i numeric(2,0), sg265x numeric(2,0), sg265z numeric(2,0), sg265aa numeric(2,0), sg265ab numeric(2,0), sg265ac numeric(2,0), sg265ad numeric(2,0), sg265ae numeric(2,0), sg265af numeric(2,0),
      sg265ag numeric(2,0), sg265ah numeric(2,0), sg265ai numeric(2,0), sg265ax numeric(2,0), sg265ay numeric(2,0), sg265az numeric(2,0), sg265bb numeric(2,0), sg266a numeric(2,0), sg266b numeric(7,0), sg267 numeric(2,0), sg268 numeric(2,0), sg269a numeric(2,0), sg269b numeric(2,0), sg269c numeric(2,0), sg269d numeric(2,0), sg269e numeric(2,0), sg269f numeric(2,0), sg269g numeric(2,0), sg269h numeric(2,0), sg269i numeric(2,0), sg269j numeric(2,0), sg269k numeric(2,0), sg269x numeric(2,0), sg269z numeric(2,0), sg270a numeric(2,0), sg270b numeric(2,0), sg270c numeric(2,0), sg270d numeric(2,0), sg270e numeric(2,0), sg270f numeric(2,0),
      sg270g numeric(2,0), sg270h numeric(2,0), sg270i numeric(2,0), sg270j numeric(2,0), sg270k numeric(2,0), sg270x numeric(2,0), sg270y numeric(2,0), sg270z numeric(2,0), sg271 numeric(2,0), sg272a numeric(2,0), sg272b numeric(7,0), sg273 numeric(2,0), sg274 numeric(6,0), sg275 numeric(2,0), sg276 numeric(4,0), sg277 numeric(2,0), sg278 numeric(2,0), sg279u numeric(2,0), sg279n numeric(2,0), sg280a numeric(2,0), sg280b numeric(7,0), sg281 numeric(2,0), sg282a numeric(2,0), sg282b numeric(2,0), sg282c numeric(2,0), sg283 numeric(6,0), sg284 numeric(2,0), sg285 numeric(2,0), sg286 numeric(6,0), sg287 numeric(2,0),
      sg288 numeric(2,0), sg289 numeric(7,0), sg290 numeric(2,0), sg291 numeric(3,0), sg292 numeric(6,0), sg292a numeric(7,0), sg301a numeric(2,0), sg301b numeric(2,0), sg301c numeric(2,0), sg301d numeric(2,0), sg301e numeric(2,0), sg301f numeric(2,0), sg301g numeric(2,0), sg301h numeric(2,0), sg301x numeric(2,0), sg302 numeric(2,0), sg303a numeric(2,0), sg303b numeric(2,0), sg303c numeric(2,0), sg304a numeric(2,0), sg304b numeric(2,0), sg304c numeric(2,0), sg304d numeric(2,0), sg304e numeric(2,0), sg304x numeric(2,0), sg305 numeric(3,0), sg306 numeric(2,0), sg307 numeric(2,0), sg308 numeric(2,0), sg309 numeric(2,0),
      sg310 numeric(2,0), sg311 numeric(3,0), singresoo numeric(8,0), singresoe numeric(7,0), sregaliap numeric(7,0), sbonifica numeric(7,0), sifuente1 numeric(8,0), sifuente2 numeric(7,0), sifuente3 numeric(7,0), sifuente4 numeric(6,0), singresotp numeric(8,0), singresoip numeric(2,0), singresoib numeric(3,0), sgastoti char(1), singresoipa numeric(2,0)
RECH8_All (reader CSV_3)
    attributes: FileCode char(7), HHID char(9), SHCOL3B number(3,0), SH223 number(3,0), SH225 number(3,0), SH226 number(3,0), SH227 number(6,0), SH227AA number(6,0), SH227AB number(6,0), SH227AC number(6,0), SH227AD number(6,0), SH227AE number(6,0), SH227AF number(6,0), SH227AG number(6,0), SH228 number(2,0), SH229 number(3,0), SH230 number(3,0), SH231 number(6,0), SH231AA number(6,0), SH231AB number(6,0), SH231AC number(6,0), SH231AD number(6,0), SH231AE number(6,0), SH231AF number(6,0), SH231AG number(6,0), SH232 number(2,0), SH233 number(3,0), SH234 number(3,0), SH235 number(6,0), SH235AA number(6,0),
      SH235AB number(6,0), SH235AC number(6,0), SH235AD number(6,0), SH235AE number(6,0), SH235AF number(6,0), SH235AG number(6,0), SH236 number(2,0), SH237 number(3,0), SH238 number(3,0), SH239 number(2,0), SH240 number(2,0)
    -> RECH8_All (writer POSTGRES_1)
RECH8_All (writer POSTGRES_1)
    attributes: filecode char(7), hhid char(9), shcol3b numeric(3,0), sh223 numeric(3,0), sh225 numeric(3,0), sh226 numeric(3,0), sh227 numeric(6,0), sh227aa numeric(6,0), sh227ab numeric(6,0), sh227ac numeric(6,0), sh227ad numeric(6,0), sh227ae numeric(6,0), sh227af numeric(6,0), sh227ag numeric(6,0), sh228 numeric(2,0), sh229 numeric(3,0), sh230 numeric(3,0), sh231 numeric(6,0), sh231aa numeric(6,0), sh231ab numeric(6,0), sh231ac numeric(6,0), sh231ad numeric(6,0), sh231ae numeric(6,0), sh231af numeric(6,0), sh231ag numeric(6,0), sh232 numeric(2,0), sh233 numeric(3,0), sh234 numeric(3,0), sh235 numeric(6,0), sh235aa numeric(6,0),
      sh235ab numeric(6,0), sh235ac numeric(6,0), sh235ad numeric(6,0), sh235ae numeric(6,0), sh235af numeric(6,0), sh235ag numeric(6,0), sh236 numeric(2,0), sh237 numeric(3,0), sh238 numeric(3,0), sh239 numeric(2,0), sh240 numeric(2,0)
RECHA_All (reader CSV_3)
    attributes: FileCode char(7), HHID char(7), SHCOLA number(2,0), SH53 number(3,0), SH54 number(2,0), SH55 number(2,0), SH56 number(3,0), SH57 number(2,0)
    -> RECHA_All (writer POSTGRES_1)
RECHA_All (writer POSTGRES_1)
    attributes: filecode char(7), hhid char(7), shcola numeric(2,0), sh53 numeric(3,0), sh54 numeric(2,0), sh55 numeric(2,0), sh56 numeric(3,0), sh57 numeric(2,0)
RECHS_All (reader CSV_3)
    attributes: FileCode char(7), HHID char(7), SH67 number(3,0), SH68 number(2,0), SH69 number(2,0), SH70 number(3,0), SH71U number(2,0), SH71N number(7,0), SH72U number(2,0), SH72N number(7,0), SH73 number(2,0), SH74 number(3,0), SH75U number(2,0), SH75N number(7,0), SH76U number(2,0), SH76N number(7,0), SH77 number(2,0), SH78 number(3,0), SH79U number(2,0), SH79N number(7,0), SH80U number(2,0), SH80N number(7,0)
    -> RECHS_All (writer POSTGRES_1)
RECHS_All (writer POSTGRES_1)
    attributes: filecode char(7), hhid char(7), sh67 numeric(3,0), sh68 numeric(2,0), sh69 numeric(2,0), sh70 numeric(3,0), sh71u numeric(2,0), sh71n numeric(7,0), sh72u numeric(2,0), sh72n numeric(7,0), sh73 numeric(2,0), sh74 numeric(3,0), sh75u numeric(2,0), sh75n numeric(7,0), sh76u numeric(2,0), sh76n numeric(7,0), sh77 numeric(2,0), sh78 numeric(3,0), sh79u numeric(2,0), sh79n numeric(7,0), sh80u numeric(2,0), sh80n numeric(7,0)
REC01.All (reader CSV_1) [off]
    attributes: FileCode char(7), CASEID char(18), V000 char(4), V001 number(4,0), V002 number(4,0), V003 number(3,0), V004 number(4,0), V005 number(8,0), V006 number(3,0), V007 number(5,0), V008 number(5,0), V009 number(3,0), V010 number(5,0), V011 number(5,0), V012 number(3,0), V013 number(2,0), V014 number(2,0), V015 number(2,0), V016 number(3,0), V017 number(5,0), V018 number(3,0), V019 number(3,0), V019A number(2,0), V020 number(2,0), V021 number(4,0), V022 number(3,0), V023 number(3,0), V024 number(2,0), V025 number(2,0), V026 number(2,0),
      V027 number(2,0), V028 number(4,0), V029 number(2,0), V030 number(3,0), V031 number(4,0), V032 number(2,0), V034 number(3,0), V040 number(4,0), V042 number(2,0), V044 char(1), G117B char(1), S903C number(2,0), V784X char(1), SH62B number(6,0), S326AB number(2,0), V763A number(2,0), S114E number(2,0), ML13F char(1), V504 number(2,0), SHH1 number(2,0), SH263 number(6,0), V851E char(1), V3A08R number(2,0), SG265B number(2,0), V851A char(1), M65L char(1), D118T number(2,0), D118XC char(1), D119K number(2,0), SG234 number(2,0),
      SG308 number(2,0), V784L char(1), B7 number(4,0), S539 number(2,0), V845 char(1), HV003 number(3,0), ML22A char(1), V704 number(3,0), SG292 number(6,0), SG302 number(2,0), M57M number(2,0), V767A char(1), SG116B number(3,0), MMC3 char(1), D103F char(1), V472E char(1), D105H number(2,0), SG228B number(2,0), SG283 number(6,0), V414J number(2,0), HV208 number(2,0), H11B number(2,0), SG265AF number(2,0), S577D number(3,0), SG269I number(2,0), V474G char(1), SLNWP number(2,0), SH6YX number(2,0), SHH1M number(3,0), SHH2 number(2,0),
      V471C char(1), HW53 number(4,0), V414Q char(1), SHH2D number(3,0), SH617 number(2,0), SH284 number(4,0), SH235AG number(6,0), SG216D number(2,0), SG242 number(2,0), D112N char(1), M42E number(2,0), SH6XY number(2,0), SH1X number(2,0), SH54 number(2,0), HC60 number(4,0), V481A char(1), V326 number(3,0), V802 number(5,0), CHL8 number(3,0), HV212 char(1), SG270I number(2,0), SINGRESOE number(7,0), SH246D number(6,0), HV001 number(4,0), SG215 number(2,0), SG265AZ number(2,0), H12I number(2,0), H32Q char(1), S523U number(2,0), SH_MIG char(15),
      H33Y number(5,0), V224 number(3,0), M42A char(1), S506A char(1), V218 number(3,0), SG201M number(2,0), S325J number(2,0), SG202D number(2,0), V161 number(3,0), SH244 number(6,0), V215 number(4,0), SHD4M number(3,0), V509 number(5,0), V510 number(2,0), S435GE number(2,0), SG220 number(2,0), M57C char(1), V414B char(1), SH284A number(4,0), HB5 number(5,0), S325M number(2,0), HML3 number(2,0), HC13 number(2,0), H40M char(1), SHT2M number(3,0), SHT3D number(3,0), V231 number(5,0), HW3 number(5,0), HC61 number(2,0), V768B char(1),
      SG228Y number(2,0), H6 number(2,0), S538P number(2,0), S540G number(2,0), SH4 number(2,0), ML13Y number(2,0), MM1 number(2,0), S540D number(2,0), HV246F char(1), S567 number(3,0), S577R number(3,0), S578I number(5,0), V474J char(1), HV105 number(3,0), HA52 number(2,0), SG201X number(2,0), SG257 number(3,0), SG304A number(2,0), SG284 number(2,0), S325FH number(2,0), V743A number(2,0), S435E number(2,0), HB2 number(5,0), V302 char(1), ML18C char(1), SG206A number(2,0), SH5 number(2,0), M2A number(2,0), M38 number(2,0), S433L number(3,0),
      V3A08O char(1), H32C number(2,0), V232 number(2,0), SH230 number(3,0), S937Z number(2,0), SH229 number(3,0), ML19F char(1), S540K number(2,0), S541B number(2,0), HV031 number(4,0), S325FD number(2,0), SG269D number(2,0), SG270D number(2,0), V843 char(1), S577K number(5,0), S578B number(9,0), SH222 number(2,0), H6Y number(5,0), V461 char(1), HV129 char(1), V3A08P number(2,0), S577P number(9,0), S578G number(3,0), V714 number(2,0), HV243D char(1), B1 number(3,0), S325D number(2,0), D118E number(2,0), HB13 number(2,0), SH110J number(2,0),
      HV121 number(2,0), M1C char(1), M8 number(3,0), ML14Z char(1), D115O number(2,0), D100A number(2,0), S541D number(2,0), M55Z number(2,0), M57H number(2,0), M2I number(2,0), M47 char(1), G117J char(1), SHMLC number(3,0), V414A char(1), SG228E number(2,0), SG115 number(2,0), HC33 number(2,0), SG222J number(2,0), SG223A number(2,0), M3G number(2,0), SG265AI number(2,0), IDXH4A number(3,0), SH9 number(2,0), V225 number(2,0), HC7 number(5,0), MM3 number(3,0), SH76U number(2,0), SG240E number(2,0), SG123H number(2,0), SG226 number(2,0),
      M2M number(2,0), M3D number(2,0), M52 number(3,0), S112A number(2,0), S541V number(2,0), SH19 number(2,0), SH20 number(2,0), SG251 number(6,0), D119XH char(1), SG305 number(3,0), HV247 number(2,0), HML12 number(2,0), S572C number(2,0), CHL4 number(3,0), SHMLD number(3,0), V538 char(1), S714BB number(2,0), S923 number(2,0), S325FZ number(2,0), SG201F number(2,0), HML32A char(1), SH68B number(3,0), SHCOLA number(2,0), V467E char(1), M57D char(1), V770P number(2,0), S573C number(3,0), V472Q char(1), V778 char(1), V478 char(1),
      V754CP number(2,0), SH231AG number(6,0), SH232 number(3,0), S540J number(2,0), M42C number(2,0), S541A number(2,0), SG216F number(2,0), SG304C number(2,0), V166 char(1), HB41 number(5,0), V744A number(2,0), V463B char(1), SH83 number(2,0), SG261 number(2,0), V770X number(2,0), SH292 number(2,0), SH110H number(2,0), S523P number(2,0), SH110G number(2,0), V762AJ char(1), V762BA char(1), S578V number(3,0), S581D number(2,0), IDXCH2 number(3,0), SG309 number(2,0), D103E char(1), HV041 number(3,0), SHRM4 number(6,0), SG241Y number(2,0), SG310 number(2,0),
      S435GB number(2,0), HV204 number(4,0), V121 number(2,0), S937F number(2,0), SG269Z number(2,0), AWFACTW number(5,0), SG270Z number(2,0), M6 number(3,0), SH2M number(3,0), V472S char(1), V474A char(1), SH3D number(3,0), S903D number(2,0), G103 number(2,0), HV253D char(1), SH197D number(2,0), HMHIDX2 number(3,0), HO101 number(2,0), ML16C char(1), SG253C number(4,0), H32D number(2,0), S523F number(2,0), SG241B number(2,0), HML32F char(1), S947 number(2,0), SH93 number(4,0), SG121 number(2,0), HSKIDX number(3,0), D120 number(3,0), V228 number(2,0),
      D123 char(1), HV115 char(1), SG112A number(7,0), M19A number(2,0), D119XE char(1), S951 number(3,0), SGRESULT number(3,0), S906A number(2,0), V233 number(2,0), V3A00L number(2,0), V537 number(3,0), HS102 number(2,0), D118XI char(1), HB12A number(6,0), G124 number(3,0), SH283T number(5,0), SH6YJ number(2,0), HV232B number(2,0), S523T number(2,0), HV243B char(1), D115H char(1), V784Q char(1), M49E char(1), CHL6 number(3,0), SH123D number(2,0), D118XD char(1), M2G number(2,0), M45 number(2,0), SG216H number(2,0), S577G1 number(3,0),
      D115R number(2,0), HV012 number(3,0), HB1 number(3,0), V104 char(1), SG228Z number(2,0), S938 number(2,0), SH227 number(6,0), HV017 number(2,0), S903Z number(2,0), S538O number(2,0), S540F number(2,0), HV235 number(2,0), SH202 number(3,0), V379 char(1), V380 char(1), S948 number(3,0), SG266B number(7,0), V413A char(1), HV027 number(2,0), V3A00Z number(2,0), V762AK char(1), V762BB char(1), H4M number(3,0), H5D number(3,0), V851B char(1), HW72 number(5,0), H37K number(2,0), S229C number(2,0), V844 char(1), HV019 number(2,0),
      HV020 number(2,0), SG126 number(7,0), SG228I number(2,0), V770I number(2,0), S906 number(2,0), S937C number(2,0), SH231AE number(6,0), D119XI char(1), S919 number(3,0), S920 number(2,0), H0M number(3,0), D118XH char(1), ML13G char(1), S578X number(9,0), S581F number(2,0), D118W number(2,0), D119N number(2,0), SG275 number(2,0), SH6YF number(2,0), M49X number(2,0), V212 number(3,0), HV226 number(3,0), HA57 number(2,0), SHHTEC number(4,0), SG123B number(2,0), V784K char(1), SG246X number(2,0), V474 char(1), H12H number(2,0), V412A number(2,0),
      M15 number(3,0), SGMUNIC char(1), SH216 number(3,0), ML13H number(2,0), ML15C char(1), V481C char(1), SH4Y number(5,0), SVALPRO number(6,0), V614 number(2,0), V3A08Z number(2,0), H37O number(2,0), S941 number(2,0), SG109 number(2,0), SG110 number(4,0), SG240I number(2,0), SH76 number(6,0), SG222Z number(2,0), S944 number(2,0), HC62 number(3,0), SH71U number(2,0), SGINTNUM number(4,0), HB55 number(2,0), S921 number(2,0), HB66 number(2,0), HA53 number(4,0), S540X number(2,0), S541O number(2,0), SHB2M number(3,0), V119 number(2,0), V120 number(2,0),
      SHB1Y number(5,0), SHB3D number(3,0), SG303B number(2,0), V158 number(2,0), S541M number(2,0), SH251AM number(3,0), V853C char(1), SG224 number(2,0), SG265D number(2,0), V316 number(5,0), SH68A number(2,0), SG246D number(2,0), HPCIDX number(3,0), S906B number(2,0), V204 number(2,0), SINGRTH number(9,0), SG232B number(6,0), M57U char(1), S937G number(2,0), D103B number(2,0), HV014 number(2,0), SREGALIAP number(7,0), H32L number(2,0), D117 char(1), M3K number(2,0), M60 number(2,0), HW18 number(3,0), S326 number(2,0), HC5 number(5,0), SHCOLC number(2,0),
      V375A char(1), V851K char(1), M65K char(1), V852B char(1), D101C number(2,0), ML19E char(1), HV228 char(1), HA11 number(5,0), V633G char(1), SG262A number(2,0), SG222B number(2,0), H2Y number(5,0), ML19Z char(1), V471D char(1), V465 char(1), SG258A number(2,0), V376 number(3,0), V471E char(1), V775 char(1), HMLIDX number(2,0), HS111 number(2,0), SH53 number(3,0), S540H number(2,0), SG246E number(2,0), S541S number(2,0), D110H char(1), HC73 number(5,0), SG229 number(3,0), S523I number(2,0), D110F char(1),
      S540L number(2,0), S541C number(2,0), V627 number(3,0), SH221 char(4), HV242 number(2,0), SH6XC number(2,0), S578K number(3,0), S579B number(5,0), SG223F number(2,0), HS108 number(2,0), SBONIFICA number(7,0), D118H char(1), HA12A number(6,0), SH80C number(3,0), H7Y number(5,0), ML13C number(2,0), SG127 number(3,0), ML0 number(2,0), V770C number(2,0), SGEDITO number(2,0), G113 char(1), V472A char(1), S945O number(2,0), V625A number(2,0), V762AI char(1), V762AR char(1), V307 number(2,0), V762BI char(1), D115XE char(1), S929 number(2,0),
      V322 number(2,0), S930 number(3,0), G117D char(1), HV238 number(3,0), SG247E number(2,0), V743F char(1), HV253A char(1), SHSMK char(1), SG279N number(2,0), S435GM number(2,0), SG123D number(2,0), H12C number(2,0), SHH2Y number(5,0), HB4 number(5,0), HA3 number(5,0), M65E char(1), S578P2 number(9,0), M71 number(4,0), B12 number(4,0), SH1H number(3,0), SH283Y number(5,0), D115XI char(1), SH28D number(3,0), SG265BB number(2,0), H12D number(2,0), V237 number(2,0), SG301A number(2,0), V855 char(1), S578Q number(3,0), HV227 char(1),
      SG123A number(2,0), V770J number(2,0), V219 number(3,0), V220 number(2,0), S572D number(2,0), SG252 number(2,0), V438 number(5,0), ML2 number(2,0), SHT1D number(3,0), V815C char(1), M57J number(2,0), S577E number(5,0), V616 number(4,0), H37J number(2,0), S903G number(2,0), SG204M number(3,0), D118A char(1), V820 char(1), SH235AA number(6,0), H12U number(2,0), MM12 char(1), S578W number(5,0), S581E number(2,0), SH235AF number(6,0), SG204A number(5,0), S541G number(2,0), HO104 number(2,0), V414I number(2,0), V367 number(2,0), SH133B number(2,0),
      HV113 char(1), V761C char(1), V774C number(2,0), D105K char(1), SH231 number(3,0), SG282B number(2,0), V762AX char(1), V762BO char(1), V238 number(2,0), S577J number(3,0), S578A number(5,0), D116 number(3,0), SH96C number(6,0), SG240A number(2,0), S229B number(2,0), SG216B number(2,0), SG216Z number(2,0), V3A00R char(1), S222 number(2,0), HV237B number(2,0), SH242C number(3,0), V3A08S number(2,0), S578M number(5,0), S579D number(3,0), SHPC1 number(5,0), H32E number(2,0), V131 char(1), M49B number(2,0), H15I number(2,0), S572 number(3,0),
      SG265Z number(2,0), ML13A number(2,0), G114 char(1), V603 number(4,0), S223B number(2,0), SG241D number(2,0), HV253Z char(1), SG123E number(2,0), V812 number(2,0), SG249A number(2,0), V412C char(1), G123 number(2,0), V321 number(2,0), HW58 char(1), HV253E char(1), SHSD1 number(5,0), SHRM1 number(6,0), HV237F number(2,0), SH9Y number(5,0), SH227AB number(6,0), V304 char(1), SG241C number(2,0), M57P number(2,0), V3A08AB char(1), HV008 number(5,0), H3M number(3,0), H4D number(3,0), SHB1M number(5,0), V604 number(2,0), SHB2D number(5,0),
      D124 char(1), ML13K number(2,0), ML14B char(1), SH614 number(2,0), D119XJ char(1), V3A08AD char(1), SQUINTIP number(2,0), V784I char(1), S937A number(2,0), V129 number(3,0), V130 number(2,0), D118M number(2,0), V472T char(1), M55E number(2,0), V474B char(1), H38 number(2,0), D119D number(2,0), HV030 number(3,0), SH25M number(3,0), V471B char(1), V629 number(3,0), SH80MI number(3,0), V838B char(1), S326AC number(2,0), MM10 char(1), SH295A number(9,0), V770R number(2,0), V3A08X number(2,0), V784V char(1), HV230A number(2,0),
      S523L number(2,0), D119V number(2,0), SH515 number(2,0), V203 number(2,0), V784A char(1), SH249 number(6,0), SH250 number(6,0), SH70 number(6,0), SH248 number(2,0), H31 number(2,0), SG217F number(2,0), V152 number(3,0), IDX95 number(2,0), SG280A number(2,0), SH295BH number(3,0), SH69 number(2,0), V841 char(1), D115I char(1), FDYSTO number(4,0), S939 number(2,0), H41B char(1), H15L char(1), H2D number(3,0), H42 number(2,0), V414T char(1), HV246C char(1), SH21 number(2,0), SG265X number(2,0), ML13J number(2,0), ML14A char(1),
      SG269E number(2,0), SG270E number(2,0), HW6 number(6,0), SGHORAF number(3,0), MM7 number(3,0), SHIDX9 number(2,0), HML14 number(2,0), B8 number(3,0), H8M number(3,0), H9D number(3,0), S435D number(2,0), SG216X number(2,0), H37F char(1), SH125A number(2,0), M1B char(1), M29 number(2,0), D119XD char(1), SH6YA number(2,0), V3A08Q number(2,0), V827 char(1), SG201E number(2,0), H9M number(3,0), HW12 number(6,0), S325CH number(2,0), S931 number(2,0), SG218 number(2,0), V477 char(1), V625 number(2,0), H15M char(1), M4 number(3,0),
      SH233 number(3,0), SH615 char(6), M13 number(3,0), V463F char(1), SG247Z number(2,0), SH79U number(2,0), SH80U number(2,0), SIFUENTE3 number(7,0), HV216 number(3,0), HB0 number(3,0), V103 char(1), S1001 number(2,0), SHT3 number(2,0), V825 char(1), D101B number(2,0), SG304E number(2,0), V847 char(1), SH268 number(2,0), H32G number(2,0), SG222X number(2,0), V714A number(2,0), SGRESP number(3,0), SHMTX number(2,0), S913 number(3,0), SH3M number(3,0), SH4D number(3,0), HV244 number(2,0), SH62 number(2,0), SHP222 number(2,0), V472D char(1),
      S911 number(2,0), V822 char(1), SG285 number(2,0), ML21C char(1), H2M number(3,0), H3D number(3,0), M1 number(2,0), SHH3M number(3,0), S943 number(2,0), HV246I number(3,0), SG217H number(2,0), H15G number(2,0), H9 number(2,0), HV102 number(2,0), V739 number(2,0), V740 char(1), HV009 number(3,0), S908 number(3,0), HV010 number(2,0), V839A char(1), V840A char(1), HML18 number(2,0), IDXML number(2,0), V235 number(2,0), ML13L number(2,0), M57I number(2,0), V762AS char(1), M49G char(1), V762BJ char(1), S572X number(2,0),
      HV219 number(2,0), HV220 number(3,0), SH197C number(2,0), SH110L number(2,0), SGHORAI number(3,0), HV253B char(1), SG265AX number(2,0), SG228G number(2,0), HV253 char(1), M55J number(2,0), D110E char(1), V3A05 char(1), D101G number(2,0), V823 number(2,0), SG304X number(2,0), V842 char(1), HML7 number(3,0), D110A number(2,0), V408 char(1), S937B number(2,0), HV140 number(2,0), D115Y number(2,0), V784U char(1), SHT1Y number(5,0), M10 number(2,0), V838C char(1), SH63 number(2,0), V409 number(2,0), V410 number(2,0), D118XG char(1),
      HV011 number(2,0), HA67 number(3,0), V467K char(1), V743B number(2,0), SHD4Y number(5,0), HVIDX number(3,0), SG217C number(2,0), SG271 number(2,0), HML1 char(1), S506AY number(5,0), V835B char(1), D115N number(2,0), S714E number(2,0), SH118A number(2,0), SH251BH number(3,0), D105F number(2,0), SG240H number(2,0), D129 char(1), SG240X number(2,0), S114GX number(3,0), V824 char(1), S573D number(3,0), V395 char(1), V405 number(2,0), V851C char(1), D121 number(2,0), S569B number(2,0), S570B number(2,0), SH251A number(9,0), V535 number(2,0),
      V216 number(2,0), HB11 number(5,0), V850A char(1), S325O number(2,0), D118I char(1), SGMINUTI number(3,0), S326AX number(2,0), D119S number(2,0), D122A number(2,0), S903F number(2,0), SG119B number(2,0), SHB3 number(2,0), SG120B number(2,0), SG272B number(7,0), SH26 number(3,0), V829 char(1), H14 number(2,0), H12P number(2,0), V830 char(1), H32I number(2,0), SH273 number(5,0), AWFACTU number(5,0), SG247C number(2,0), HMLC number(3,0), SH80M number(3,0), SINGRTHP number(9,0), HV237K char(1), M39A number(2,0), V633A char(1), S523B number(2,0),
      S928 number(2,0), SH118B number(2,0), HA50 char(1), V3A08AC char(1), S583B number(3,0), V536 number(2,0), S541R number(2,0), V762AN char(1), V762BE char(1), HV116 number(2,0), SG235 number(2,0), SH78A number(6,0), M55K number(2,0), HML32G char(1), V3A08B number(2,0), SH6YE number(2,0), SG222K number(2,0), M65D char(1), MMC4 char(1), S577O number(5,0), S578F number(9,0), HV236 char(1), SG223B number(2,0), SG304D number(2,0), SH80AI number(5,0), H8Y number(5,0), H12J number(2,0), S435GK number(2,0), SH284G number(4,0), SG254 number(3,0),
      G106 number(3,0), CHL7 number(2,0), B10 number(2,0), V217 char(1), V472N char(1), D118P number(2,0), V527 number(4,0), D119G number(2,0), V784B char(1), D101J char(1), V784C char(1), S578P number(3,0), S579G number(9,0), HA35 char(1), SG118A number(7,0), SHBM number(5,0), SG208B number(7,0), SH3 number(2,0), H12Z number(2,0), D125 char(1), V472U char(1), V474C char(1), SG311 number(3,0), S523S number(2,0), HC32 number(5,0), SG301F number(2,0), V376A char(1), HV013 number(3,0), HV237E number(2,0), SHDISTRICT number(3,0),
      V414F number(2,0), H4Y number(5,0), SG105 number(2,0), SG269K number(2,0), S578Y number(3,0), S581G number(2,0), HV209 number(2,0), D101H char(1), SHD4 number(2,0), HV210 number(2,0), SG270K number(2,0), SH1Y number(5,0), SH55 number(2,0), V472R char(1), BORD number(3,0), HB58 char(1), SH238 number(6,0), HD101 number(4,0), SG123C number(2,0), ML13P char(1), V631 char(1), S28DAYS number(2,0), S714D number(2,0), H37G char(1), D105C number(2,0), SH9M number(3,0), ML15B char(1), SG256A number(2,0), V762BU char(1), MM14 number(3,0),
      H37A number(2,0), S540E number(2,0), HV218 number(2,0), SH234C number(6,0), HC52 number(2,0), HB3 number(5,0), V624 number(3,0), S577L number(9,0), S578C number(3,0), V762AC char(1), MMC1 number(3,0), SG222C number(2,0), S114B number(2,0), SH2X number(2,0), SG223E number(2,0), H5Y number(5,0), G117H char(1), M27 number(2,0), SHT2Y number(5,0), M65X char(1), HC12 number(6,0), V472G char(1), V415 number(2,0), SH212D number(2,0), H43 number(2,0), S435H number(4,0), V719 number(2,0), V454 number(2,0), B2 number(5,0), S435GF number(2,0),
      ML24C char(1), V761B char(1), H3Y number(5,0), SINGRESOIB number(3,0), H12G number(2,0), HV118 number(2,0), ML13Z number(2,0), S1004 number(2,0), H7 number(2,0), SH6YB number(2,0), HW51 number(3,0), H32J number(2,0), SHB13 number(2,0), V3A08L number(2,0), V613 number(3,0), V414W char(1), ML19A char(1), ML20A number(2,0), SHA0 number(3,0), SHRM3 number(6,0), SHSD3 number(5,0), SG241Z number(2,0), V468 number(2,0), SG301E number(2,0), SH295BM number(3,0), V234 number(2,0), V836 char(1), G119 number(2,0), HB32 number(5,0), V3A01 char(1),
      S584B number(3,0), M55C number(2,0), MM11 char(1), HA33 number(2,0), S937X number(2,0), HC11 number(5,0), V412B char(1), HA6 number(6,0), SH127B number(5,0), HA41 number(5,0), H2 number(2,0), S907 number(2,0), S573E number(5,0), S576C number(5,0), V3A08G number(2,0), S581J number(2,0), D107 number(2,0), V472H char(1), V784S char(1), SG237A number(2,0), IDX5CS number(3,0), V528 number(3,0), V325A char(1), V832C char(1), V853B char(1), MM8 number(5,0), D110C number(2,0), SH226 number(3,0), SG123X number(2,0), V467M char(1),
      SG219A number(2,0), HO106 number(2,0), V732 number(2,0), HV253G char(1), SHH3Y number(5,0), B4 number(2,0), HV230B number(2,0), D118XK char(1), HB40 number(5,0), V763C number(2,0), V767C char(1), V419 number(2,0), V420 char(1), ML101 char(1), S326AA number(2,0), S940M number(3,0), HV246J char(1), SG240D number(2,0), HB63 number(2,0), S541X number(2,0), M70 number(2,0), G112 char(1), M36 char(1), D115K number(2,0), M42B char(1), SG225B number(7,0), V762AF char(1), V744D number(2,0), SH127A number(2,0), B5 number(2,0),
      S522D number(2,0), V467L char(1), V851F char(1), HW17 number(3,0), H20 number(2,0), SH80A number(5,0), SG278 number(2,0), M3M number(2,0), M62 number(2,0), S581I number(2,0), V157 number(2,0), S1113 number(2,0), S926 number(2,0), SG113D number(6,0), V359 number(3,0), V360 number(3,0), V834C char(1), HV000 char(4), SG233 number(2,0), H36A number(2,0), SG223Z number(2,0), SG304B number(2,0), SH139C number(3,0), HV246H number(3,0), HC8 number(5,0), V762AP char(1), V762BG char(1), D127 char(1), D105E number(2,0), V481F char(1),
      HA62 char(1), SG223G number(2,0), SH139B number(3,0), SH231AC number(6,0), H12S number(2,0), V469E number(2,0), V851D char(1), V815A char(1), SG207B number(2,0), V762AH char(1), V302A number(2,0), S578U number(3,0), H12Y number(2,0), S581C number(2,0), SG247X number(2,0), SG241G number(2,0), M55I number(2,0), V414P number(2,0), M57N number(2,0), M49Z number(2,0), SG202H number(2,0), V446 number(5,0), V3A00K number(2,0), S573A number(2,0), HV239 char(1), HV240 char(1), HB35 number(3,0), V413D char(1), V784O char(1), M57L number(2,0),
      H6M number(3,0), H7D number(3,0), V418 number(2,0), S506AD number(3,0), HV213 number(3,0), SH68C number(3,0), SH197E number(2,0), V211 number(5,0), V311 char(1), V784F char(1), V472K char(1), V473B char(1), S325CB number(2,0), HA5 number(5,0), SG219B number(7,0), SINGRESOO number(8,0), M55L char(1), S577G2 number(5,0), V848 char(1), SG211 number(2,0), ML23A number(2,0), V122 number(2,0), S940Y number(5,0), D101E number(2,0), HW52 number(2,0), SG243A number(2,0), HML31 number(2,0), ML13X number(2,0), V414H number(2,0), VCAL char(73),
      S540I number(2,0), V805 number(4,0), M2B number(2,0), M39 number(2,0), G117Y char(1), SH128 number(3,0), SH68 number(2,0), HMLD number(3,0), D119T number(2,0), D122B number(2,0), H15C number(2,0), V750 number(2,0), D118C number(2,0), V754JP number(2,0), S573 number(3,0), SGINTM number(3,0), SH2D number(3,0), SH1M number(3,0), H37M number(2,0), V849 char(1), SG269C number(2,0), V754BP char(1), SG270C number(2,0), M1D number(3,0), M57T number(2,0), SH251 number(2,0), SH6XA number(2,0), HB51 number(3,0), V846 char(1), SG269B number(2,0),
      SG270B number(2,0), SG228C number(2,0), D118XJ char(1), SH215 number(3,0), M57A number(2,0), SG223K number(2,0), V770D number(2,0), V134 number(2,0), G109 char(1), G110 char(1), SH3H number(3,0), SH56 number(3,0), SG258B number(7,0), S523R number(2,0), D118Y number(2,0), D119P number(2,0), S325FX number(2,0), HML32B char(1), SH74 number(6,0), SH3X number(2,0), SG269X number(2,0), SG270X number(2,0), H32T number(2,0), S510J number(2,0), SH128B number(5,0), V3A00F number(2,0), HA69 char(1), HA70 char(1), V853A char(1), SGSUPERV number(4,0),
      G111 char(1), D119XG char(1), H41A char(1), SH71 number(3,0), D119W number(2,0), SG241I number(2,0), V409A char(1), V410A char(1), MMC5 number(3,0), D115B number(2,0), SG201J number(2,0), SG202A number(2,0), SH69A number(2,0), V471F char(1), V437 number(5,0), H32F number(2,0), HV023 number(3,0), HV101 number(3,0), ML19D char(1), SH279 number(2,0), SH280 number(5,0), V242 number(5,0), D110D char(1), S523D number(2,0), S903H number(2,0), SG107 number(2,0), HV040 number(4,0), HML30 number(3,0), V414V number(2,0), S577Q number(3,0),
      S578H number(3,0), V463X char(1), V472C char(1), SG264 number(2,0), H37N number(2,0), S435F number(2,0), G117X char(1), SH6YI number(2,0), M55X number(2,0), M57F number(2,0), S924 number(3,0), V769 char(1), V770 number(2,0), V3A02 char(1), V3A00H number(2,0), V202 number(2,0), SG227 number(6,0), M2K number(2,0), M55M char(1), V141 number(2,0), M3B number(2,0), M50 number(2,0), V323A number(3,0), S572B number(2,0), SHP216 number(3,0), V414E number(2,0), SGMINUTF number(3,0), SH6M number(3,0), S439A number(3,0), SH7D number(3,0),
      V462 char(1), SH92 number(3,0), SH259 number(6,0), HA1 number(3,0), SH260 number(6,0), V837 char(1), V213 number(2,0), V458 char(1), ML22B char(1), SH235AC number(6,0), S435GG number(2,0), H37Z number(2,0), SG113A number(6,0), HV106 number(2,0), V701 number(2,0), V633B char(1), V439 number(5,0), V440 number(5,0), V602 number(2,0), SH7M number(3,0), SH8D number(3,0), D103D char(1), SG217E number(2,0), V634 char(1), SG240Z number(2,0), S903E number(2,0), HB53 number(4,0), V784D char(1), SH251BM number(3,0), HV232D number(2,0),
      SG222F number(2,0), HV237 number(2,0), V312 number(3,0), ML22C char(1), HA56 number(4,0), SG116A number(3,0), ML13D number(2,0), D118L number(2,0), D119C number(2,0), H36F char(1), HML17 number(2,0), SG201D number(2,0), MMIDX number(3,0), V774B number(2,0), D100D number(2,0), HML2 char(1), H31C number(2,0), V502 number(2,0), D105A number(2,0), SH1MO number(3,0), B11 number(4,0), V833B char(1), M49Y number(2,0), HC51 number(3,0), SGINT number(9,0), M55G number(2,0), H10 number(2,0), ML13M number(2,0), V803 number(3,0), SG240B number(2,0),
      SH67 number(3,0), M57R number(2,0), HC19 number(5,0), D115XJ char(1), ML16A number(2,0), SH77C number(6,0), SVIVIG2 number(2,0), SG262B number(6,0), SH75U number(2,0), V384A number(2,0), S936 number(2,0), SH268I number(4,0), HS107 number(2,0), V756 number(2,0), M73 number(3,0), S114C number(2,0), D115G number(2,0), M65H char(1), V413B char(1), SH235AD number(6,0), HML11 number(2,0), V754DP number(2,0), V768C char(1), HV109 number(2,0), HW10 number(5,0), HV110 char(1), S591 number(3,0), V745A char(1), G117C char(1), SHED3 number(2,0),
      V3A00P char(1), V337 number(3,0), V761 char(1), V784H char(1), SG116C number(3,0), V784J char(1), SG217I number(2,0), SH8 number(2,0), V762AE char(1), S568E number(2,0), HV246 number(2,0), SVIVIG1 number(2,0), SG208A number(2,0), HV237X number(2,0), SH79 number(3,0), SH80 number(4,0), V411A number(2,0), HO103 number(2,0), V839 char(1), V840 char(1), SG265AB number(2,0), M3H number(2,0), SG247Y number(2,0), V457 number(2,0), V472O char(1), SG279U number(2,0), SG282C number(2,0), V762AV char(1), V762BM char(1), SG111 number(3,0),
      HV122 number(2,0), HV225 number(2,0), HW70 number(5,0), HV127 char(1), SG288 number(2,0), SH78 number(2,0), M5 number(3,0), SH1 number(14,0), V153 number(2,0), V472L char(1), HB52 number(2,0), MM5 char(1), V814 number(2,0), H0D number(3,0), H22 number(2,0), S569D number(2,0), S435GL number(2,0), V159 number(2,0), V160 number(2,0), S570D number(2,0), S306A number(2,0), M2F number(2,0), M44 char(1), SHCMC number(4,0), IDX92 number(3,0), HV007 number(5,0), SG256B number(6,0), SH3Y number(5,0), SH75 number(2,0), V633E char(1),
      SH227AG number(6,0), ML13E number(2,0), V762AO char(1), M57V char(1), V762BF char(1), SH295AD number(3,0), V414C char(1), D118V number(2,0), D119M number(2,0), HML32D char(1), HA65 number(2,0), V102 number(2,0), SHT2 number(2,0), V762BZ char(1), SH258 number(3,0), SG217Y number(2,0), S114G number(2,0), H37L number(2,0), V762AQ char(1), V762BH char(1), SH271 number(5,0), V3A00N number(2,0), SH94 number(6,0), H32X number(2,0), S576A number(3,0), S823B number(2,0), D118X number(2,0), D119O number(2,0), SH122C number(5,2), HC17 number(3,0),
      SG280B number(7,0), V124 number(2,0), V482B char(1), D130A char(1), HV207 number(2,0), SH91 number(2,0), HV044 char(1), SG216A number(2,0), H37D number(2,0), V467G char(1), SH133C number(2,0), SG265H number(2,0), V414D char(1), V3A00J number(2,0), V731 number(2,0), S577C number(3,0), V3A08N number(2,0), S576H number(9,0), HW8 number(5,0), SG202G number(2,0), ML1 number(3,0), HB56 number(4,0), SG228D number(2,0), BIDX number(3,0), H12K number(2,0), H13B number(2,0), V762AW char(1), V762BN char(1), SH8Y number(5,0), SH227AE number(6,0),
      SG222I number(2,0), SG237B number(6,0), SG241E number(2,0), V763E char(1), V137 number(2,0), S325A number(2,0), SH516 char(6), S541Y number(2,0), V138 number(2,0), D119XA number(2,0), HV246G number(3,0), V128 number(3,0), S536K number(2,0), SG281 number(2,0), V476 char(1), V207 number(2,0), REC84_GROUP char(1), HML5 number(2,0), G121 number(2,0), G107 number(3,0), HC58 char(1), SH224I number(4,0), D115S number(2,0), D117A number(2,0), IDX99 number(2,0), HIDX number(2,0), IDX96 number(2,0), SG269F number(2,0), SG270F number(2,0), SG207 number(3,0),
      HMLB number(3,0), S325CX number(2,0), HV103 number(2,0), M49A number(2,0), H12L number(2,0), HV221 number(2,0), HV246A char(1), HV237C number(2,0), HV246E char(1), V784T char(1), V744B number(2,0), S5YEARS number(2,0), V3A08A char(1), S325CE number(2,0), S916 number(2,0), S570 number(3,0), HC53 number(4,0), CHL5 number(2,0), V447A number(3,0), V3A04 char(1), V414R char(1), S575 number(9,0), HMLA number(3,0), SINGRESOTP number(8,0), S541E number(2,0), V784E char(1), V3A08F number(2,0), S103A number(2,0), SG277 number(2,0), H32A number(2,0),
      SH73 number(6,0), SG301H number(2,0), SG202X number(2,0), V227 number(2,0), H32P number(2,0), V768A char(1), V481B char(1), HS104 number(2,0), SG245 number(2,0), V813 number(2,0), SH2MO number(3,0), S578P1 number(5,0), SG248 number(2,0), S616 number(3,0), SG104 number(2,0), SH505 number(4,0), M49C char(1), HML34 char(6), SH79N number(7,0), SH80N number(7,0), G101 number(2,0), SH6YC number(2,0), S927 number(2,0), B13 number(2,0), V762AM char(1), V762AA char(1), V541 char(1), V481D char(1), V762BD char(1), SHB1D number(3,0),
      HC3 number(5,0), SH255D number(4,0), SH257 number(3,0), FSYSTO number(4,0), S904 number(2,0), SG230M number(3,0), SG201I number(2,0), V832B char(1), SINGRESOIP number(2,0), HB60 number(2,0), HB68 number(2,0), S540W number(2,0), S541N number(2,0), V811 number(2,0), V406 number(2,0), SG214 number(2,0), HML16A number(3,0), S714BC number(2,0), G118 number(2,0), D118Q number(2,0), D119H char(1), D119X number(2,0), SG286 number(6,0), V474D char(1), M55O char(1), SG253B number(4,0), S541L number(2,0), V466 char(1), V784P char(1), H12R char(1),
      M3J number(2,0), SHP221 number(4,0), SG202N char(1), HML16 number(3,0), SH76N number(7,0), HV128 char(1), HW5 number(5,0), V414K number(2,0), V715 number(3,0), V770V number(2,0), SG123J number(2,0), MIDX number(2,0), S909 number(2,0), S910 number(2,0), SHT3M number(3,0), D130B char(1), V444A number(5,0), SG216E number(2,0), D103C char(1), H31E number(2,0), D115E number(2,0), S903X number(2,0), SH110K number(2,0), SH295BC char(6), S582 number(2,0), V3A00C number(2,0), S325FA number(2,0), S578J number(9,0), S579A number(3,0), SG117A number(7,0),
      S576J number(3,0), S577A number(5,0), SHADULT35 number(2,0), SH242B number(2,0), SH223 number(3,0), ML19X char(1), D114 number(2,0), SHMLB number(3,0), SHED1 number(2,0), V529 number(4,0), V530 number(2,0), V511 number(3,0), IDXCHL number(3,0), SG225A number(2,0), S918 number(2,0), SG239 number(2,0), SIFUENTE2 number(7,0), V770L number(2,0), V413C char(1), SH255S number(4,0), S523G number(2,0), V503 number(2,0), S325CG number(2,0), H15H number(2,0), SHUPAZILA number(3,0), V3A00Q char(1), V763G char(1), SGZONA number(2,0), SH61 number(3,0), D101D number(2,0),
      M57Q number(2,0), V774A number(2,0), V3A06 char(1), V481E char(1), H12V number(2,0), SG201A number(2,0), D115XF char(1), SG201B number(2,0), AWFACTT number(5,0), SHP4D number(3,0), H32U number(2,0), V834B char(1), S541Q number(2,0), SH2 number(2,0), M42D number(2,0), SG101 number(3,0), HC1 number(3,0), V826A char(1), H3 number(2,0), S541K number(2,0), SH6YG number(2,0), V463G char(1), V3A00D number(2,0), D118S number(2,0), D119J number(2,0), D121A number(2,0), S522C number(2,0), SH231AD number(6,0), AWFACTE2 number(6,0), S932 number(2,0),
      HV206 number(2,0), SH123A number(2,0), SH198C number(2,0), D005 number(8,0), D119XK char(1), SH6YD number(2,0), H7M number(3,0), V3A00S number(2,0), M57X number(2,0), H8D number(3,0), V741 number(2,0), M17 number(2,0), V779 char(1), V780 char(1), MM15 char(1), D105D number(2,0), SG125 number(2,0), SG282A number(2,0), SH28C number(2,0), V464 char(1), HS105 number(2,0), SIFUENTE1 number(8,0), MMC2 number(3,0), REC31_GROUP number(2,0), V414N number(2,0), V3A03 char(1), S572A number(2,0), SH234 number(2,0), SH7 number(2,0), HML15 char(1),
      V507 number(3,0), S566 number(2,0), SHMLA number(3,0), ML13O char(1), SH283 number(9,0), SG240C number(2,0), SG241A number(2,0), H15B number(2,0), S577G number(3,0), SG241F number(2,0), G117A char(1), G104 number(2,0), D110G char(1), H31D number(2,0), SH283D number(3,0), D108 number(2,0), SG265AC number(2,0), V762AB char(1), V3A00W number(2,0), D101I char(1), S604A number(3,0), S578N number(9,0), S579E number(3,0), HV245 number(4,0), SH251B number(5,0), V838A char(1), HV237Z number(2,0), S922 number(2,0), D115W number(2,0), H37E number(2,0),
      V482A char(1), H13 number(2,0), HA13 number(2,0), SH242A number(6,0), SH264D number(4,0), SG202M number(2,0), M55H number(2,0), V762AT char(1), V762BK char(1), G108 number(3,0), H0 number(2,0), V474E char(1), HV026 number(2,0), SHP218 number(3,0), SH228 number(2,0), SG217Z number(2,0), M55B number(2,0), SHB2Y number(5,0), D115L number(2,0), V481H char(1), V455 number(2,0), G115 char(1), G122 number(3,0), HV004 number(4,0), SG114A number(7,0), SH139D number(3,0), D118D number(2,0), V763F char(1), V190 number(2,0), D105I number(2,0),
      D118B number(2,0), S435GA number(2,0), S325CC number(2,0), SHB3M number(3,0), SH251AY number(5,0), M55N char(1), V744E number(2,0), S578S number(5,0), S581A number(3,0), S946 number(2,0), SG241H number(2,0), HA12 number(6,0), HB57 number(2,0), V3A00V number(2,0), HS101 number(2,0), S541I number(2,0), V372A number(2,0), V106 number(2,0), H0Y number(5,0), H45 char(1), HV202 char(1), M2D number(2,0), SHB1 number(3,0), V363 number(3,0), SH94A number(2,0), M2N number(2,0), M3E number(2,0), D118XB char(1), SG247B number(2,0), M49F char(1),
      SH253 number(5,0), HML32E char(1), D100B number(2,0), HO105 number(2,0), HV234A number(2,0), HA54 number(2,0), HV107 number(2,0), SG244 number(2,0), V3A08J number(2,0), V3A09A char(1), HV246D char(1), ML11 char(1), S577F number(9,0), SG265AD number(2,0), V474H char(1), IDXHML number(2,0), SG238 number(2,0), V208 number(2,0), S576F number(3,0), S435C number(2,0), HS103 number(2,0), HW13 number(2,0), S577N number(3,0), S578E number(5,0), SHH2M number(3,0), SHH3D number(3,0), HV018 number(4,0), V763D char(1), S578R number(3,0), HD100 number(3,0),
      AWFACTE number(5,0), V632 number(2,0), V412 char(1), S569A number(2,0), S570A number(2,0), S576E number(3,0), V467H char(1), S580 number(3,0), SH96A number(6,0), V472P char(1), HV032 number(2,0), SH221AH number(3,0), HV237I char(1), HA55 number(2,0), SH241 number(6,0), V3A08V number(2,0), ML14Y char(1), V3A00A number(2,0), D119XB char(1), V3A08D number(2,0), HA0 number(3,0), V243 number(2,0), D115J number(2,0), SH0Y number(5,0), SGWEIGHT number(9,0), SG263 number(2,0), SH104A number(2,0), CHL1 number(2,0), HW56 number(5,0), HV016 number(3,0),
      S937E number(2,0), H37H number(2,0), SG265AY number(2,0), SG291 number(3,0), SH28 number(3,0), ML16B char(1), V414U char(1), SG269H number(2,0), S541P number(2,0), SG270H number(2,0), D1310A number(2,0), HC68 number(5,0), SHB3Y number(5,0), SG265C number(2,0), SG287 number(2,0), SH227AD number(6,0), ML19C char(1), SGPROVIN number(3,0), ML20C char(1), SHT1M number(3,0), H5M number(3,0), H6D number(3,0), SHT2D number(3,0), HV253X char(1), H32Y number(2,0), M65G char(1), D115U char(1), V3A08E number(2,0), SG119A number(7,0), SG120A number(6,0),
      ML19Y char(1), SH231AF number(6,0), HW71 number(5,0), SG223Y number(2,0), HMHIDX number(3,0), S325CZ number(2,0), S540A number(2,0), S435J number(2,0), S934 number(2,0), SH231AB number(6,0), SG221 number(2,0), S229A number(2,0), S325CA number(2,0), SG202K number(2,0), V3A07 number(3,0), SGINTD number(3,0), IDX9A number(3,0), SG203B number(3,0), V469X number(2,0), V472F char(1), AWFACTR number(5,0), V702 number(3,0), HC10 number(5,0), V417 number(2,0), V834A char(1), S905Y number(5,0), H44C char(1), D119Q number(2,0), V474F char(1), HV006 number(3,0),
      SH2H number(3,0), V851I char(1), V626 number(3,0), SH231AA number(6,0), SG217B number(2,0), HA63 char(1), S589 number(3,0), S523J number(2,0), S569E number(2,0), D105M char(1), HV243C char(1), SCORE number(3,0), D115T number(2,0), B16 number(3,0), SG202F number(2,0), SG123F number(2,0), H12M number(2,0), S506AM number(3,0), D115XD char(1), SH235AB number(6,0), HV246B number(3,0), SHFLG number(2,0), D118N number(2,0), D119E number(2,0), HV270 number(2,0), S410J number(3,0), M57B number(2,0), SH90 number(2,0), V362 number(2,0), SH33 number(2,0),
      V3A08T number(2,0), M2H number(2,0), M46 number(4,0), V319 number(2,0), V705 char(1), V320 number(2,0), HW2 number(5,0), V826 char(1), S823A number(2,0), M3F number(2,0), M54 number(2,0), V301 char(1), M49D char(1), S714BA number(2,0), V762BS char(1), V717 char(1), V785 number(2,0), S588 number(2,0), SG117B number(2,0), M9 number(3,0), SH23 number(3,0), HB33 number(2,0), SH286 number(2,0), HO102 number(2,0), H34 number(2,0), SG223H number(2,0), V472I char(1), D115XA number(2,0), HML21 number(2,0), HW57 number(2,0),
      V770F number(2,0), M19 number(5,0), SG253 number(4,0), D115XB char(1), V721 char(1), V421 char(1), V318 number(2,0), D119U char(1), D122C number(2,0), SH239 number(6,0), SH240 number(2,0), MM6 number(3,0), V766A char(1), HML6 number(2,0), SG268 number(2,0), SH133A number(3,0), S573B number(9,0), D104 number(2,0), HA32 number(5,0), ML15A number(2,0), SH218 number(3,0), V467A char(1), ML23B char(1), HA60 char(1), S435GZ number(2,0), HV042 number(2,0), V828 char(1), MM2 number(2,0), V445 number(5,0), HV124 number(3,0),
      H36C number(2,0), HC27 number(2,0), HV237D number(2,0), V113 number(3,0), SHH3 number(2,0), SGHOGAR number(3,0), D115XH char(1), SG123I number(2,0), V123 number(2,0), SG128 number(2,0), HML8 number(2,0), SH57 number(2,0), V393 char(1), HMLE char(1), S714AA number(2,0), V136 number(3,0), S435GH number(2,0), S325B number(2,0), V532 number(2,0), S1002 number(2,0), SG213B number(7,0), SG307 number(2,0), V833A char(1), SH4M number(3,0), SH5D number(3,0), HHID char(7), SH72 number(6,0), MM4 number(5,0), SH24 number(2,0), SG265AG number(2,0),
      S523O number(2,0), SG201H number(2,0), SH62A number(2,0), V447 number(2,0), V475 char(1), S523A number(2,0), D118XE char(1), SH25 number(2,0), HC15 number(2,0), SG232A number(2,0), SH295 number(2,0), SH25Y number(5,0), ML13B number(2,0), SH227AC number(6,0), S942 number(3,0), SH616 number(2,0), M1A number(2,0), M28 number(2,0), HC0 number(3,0), V115 number(4,0), S523N number(2,0), D115M number(2,0), SH27 number(2,0), H21A number(2,0), V139 number(3,0), V140 number(2,0), HO107 number(2,0), H32V number(2,0), H33M number(3,0), H40D char(1),
      SH221B number(4,0), SG265AA number(2,0), V501 number(2,0), HS106 number(2,0), SG112B number(2,0), S523C number(2,0), HV237A number(2,0), B15 number(2,0), SG223X number(2,0), M1E number(5,0), HML32 number(2,0), S540B number(2,0), HA66 number(2,0), H32N number(2,0), S541J number(2,0), V471G char(1), SCHL145 number(2,0), V443 number(6,0), S223A number(2,0), S326B number(3,0), HC2 number(5,0), SG265G number(2,0), V801 number(5,0), AWFACTE3 number(6,0), SH72U number(2,0), HB65 number(2,0), V474I char(1), SH72N number(7,0), S541T number(2,0), D119R number(2,0),
      SH251AD number(3,0), SGEDITC number(4,0), SG116D number(3,0), V777 char(1), V411 number(2,0), SG223I number(2,0), ML21A char(1), SG270Y number(2,0), HV123 number(2,0), HV237G number(2,0), SH0 number(2,0), SG301B number(2,0), D128 char(1), H40Y char(1), H37Y number(2,0), S435I number(2,0), S577I number(3,0), SG202I number(2,0), S576I number(3,0), S945 number(2,0), SGASTOTI char(1), SG231 number(3,0), S902 number(2,0), SG246B number(2,0), S325CD number(2,0), D119XF char(1), SH276 number(2,0), V467B char(1), V831 char(1), SHP221AH number(3,0),
      HV217 number(2,0), D112A number(2,0), S569C number(2,0), S823 number(2,0), S570C number(2,0), HV025 number(2,0), SH220B char(4), S523E number(2,0), S905M number(3,0), SH77 number(2,0), H32R char(1), SH77A number(6,0), SG122 number(2,0), SG216I number(2,0), V414G number(2,0), HWIDX number(2,0), V762BR char(1), S933 number(2,0), D101A number(2,0), V463Z char(1), IDX98 number(2,0), V101 number(2,0), S576D number(9,0), V414L number(2,0), SHT1 number(2,0), H31B number(2,0), D115V number(2,0), HW15 number(2,0), V626A number(3,0), V394 char(1),
      V404 number(2,0), V384C number(2,0), HML35 number(2,0), SH251BC char(6), SHB2 number(3,0), V531 number(3,0), S577B number(9,0), V317 number(5,0), V471A char(1), HA40 number(5,0), M57G number(2,0), S325FE number(2,0), SH6YH number(2,0), H44A number(3,0), SH254 number(3,0), SG228X number(2,0), SG269A number(2,0), HV232 number(2,0), SG270A number(2,0), SG222D number(2,0), SG274 number(6,0), V416 char(1), SG303A number(2,0), SG113B number(6,0), V456 number(4,0), SG114B number(7,0), HO100 number(3,0), HML32C char(1), S587 number(3,0), S581X number(2,0),
      V815B char(1), M2J char(1), M3A number(2,0), M48 char(1), HW4 number(5,0), S1003 number(2,0), SHCOL21A number(3,0), HV126 char(1), HV253C char(1), V467D char(1), HV205 number(3,0), V444 number(6,0), SHP4Y number(5,0), HV246K char(1), HA68 number(2,0), SH286I number(4,0), SG222H number(2,0), SH295AM number(3,0), S803A number(2,0), V472B char(1), ML23C char(1), SG209 number(2,0), SG210 number(2,0), V835C char(1), SH5M number(3,0), SH6D number(3,0), SH227AA number(6,0), SH82 number(2,0), SH264S number(4,0), V762AU char(1),
      V762BL char(1), SH224 number(2,0), HV120 number(2,0), V525 number(3,0), SG222A number(2,0), H32S number(2,0), B0 number(2,0), SH139E number(3,0), V762BT char(1), SH63B number(2,0), V770K char(1), SG228J number(2,0), SG230A number(5,0), SH295B number(5,0), SG241X number(2,0), V3A00X number(2,0), V223 number(2,0), V767B char(1), V770U number(2,0), SHED2 number(3,0), SG223C number(2,0), V3A08I number(2,0), D115X number(2,0), SH77B number(6,0), V743C char(1), HML33 char(1), S114F number(2,0), S586 number(2,0), V513 number(2,0), V442 number(6,0),
      SH33D number(3,0), SH6XX number(2,0), HW11 number(5,0), SH13 number(2,0), V804 number(2,0), S578L number(3,0), S579C number(9,0), D115D number(2,0), H37P number(2,0), S523Q number(2,0), SG259 number(2,0), SG260 number(2,0), V441 number(6,0), SG265F number(2,0), HV232E char(1), SH212 number(4,0), V3A00B number(2,0), D115F number(2,0), G105 number(2,0), HV237J char(1), H32M number(2,0), H33D number(3,0), D100C number(2,0), HB69 number(8,0), HB70 number(4,0), SH128A number(2,0), HS100 number(2,0), SG202J number(2,0), SG203A number(2,0), M65F char(1),
      SH6Y number(5,0), MM9 number(3,0), V229 number(3,0), V230 number(5,0), D118O number(2,0), D119F number(2,0), D112 number(2,0), HC30 number(3,0), S519J number(2,0), HML4 number(3,0), HB12B number(6,0), V762AZ char(1), V762BQ char(1), V770M number(2,0), S912 number(2,0), V226 number(4,0), V481X char(1), H15F number(2,0), D118XA number(2,0), SH206 number(5,0), SINGRHI number(2,0), SG217A number(2,0), CHL2 number(3,0), SG289 number(7,0), V784M char(1), SG290 number(2,0), HA12B number(6,0), V835A char(1), HW1 number(3,0), SH7Y number(5,0),
      V3A00U number(2,0), M57E number(2,0), M57K number(2,0), B6 number(4,0), HDPIDX2 number(2,0), SH198D number(2,0), S914 number(2,0), M55F number(2,0), SH603 number(6,0), G117G char(1), HC9 number(6,0), SH6XZ number(2,0), S114A number(2,0), H12A number(2,0), SG269J number(2,0), SG270J number(2,0), V754WP number(2,0), M66 number(2,0), SHCOLB number(2,0), HML13 number(2,0), ML13I number(2,0), V806 number(2,0), V221 number(4,0), SG265I number(2,0), V770E number(2,0), S581H number(2,0), V3A00O number(2,0), H47 number(2,0), V851J char(1), V852A char(1),
      V821C char(1), S571 number(2,0), S584 number(3,0), V168 char(1), V133 number(3,0), V191 number(8,0), V201 number(3,0), V3A08U number(2,0), H46A number(3,0), V414O number(2,0), H11 number(2,0), V762AL char(1), V304A char(1), V762BC char(1), SG301X number(2,0), SH235 number(2,0), HV112 char(1), SH295AY number(5,0), V214 number(2,0), V729 number(2,0), V730 number(3,0), H12N number(2,0), V467F char(1), S578T number(9,0), S581B number(5,0), D119XC char(1), H32W number(2,0), V474Z char(1), HC64 number(3,0), SG265A number(2,0),
      SG265AE number(2,0), SG223J number(2,0), V426 number(4,0), HW73 number(5,0), S536A number(2,0), V327 number(2,0), V784G char(1), S325E number(2,0), D118K number(2,0), D119B number(2,0), S523X number(2,0), V361 number(2,0), SH2Y number(5,0), D118G number(2,0), SH618 char(6), SH205 number(5,0), SG201N number(2,0), SG202E number(2,0), SG223D number(2,0), HV271 number(8,0), V481G char(1), V222 number(4,0), SG222G number(2,0), SINGRESOIPA number(2,0), D115XK char(1), SH81 number(3,0), SH0D number(3,0), SH22 number(2,0), SG240G number(2,0), HC57 number(2,0),
      SG265E number(2,0), S523H number(2,0), V467J char(1), V770H number(2,0), V467I char(1), S325FC number(2,0), V459 char(1), V460 char(1), S945A number(2,0), HC4 number(5,0), H33 number(2,0), HW19 number(5,0), SG240F number(2,0), S541U number(2,0), H15J char(1), HDPIDX number(3,0), S229D number(3,0), V481 char(1), V633C char(1), H12Q char(1), V850B char(1), D126 char(1), V633D char(1), V762BP char(1), SH3MO number(3,0), V3A00M number(2,0), HA51 char(1), M3N number(2,0), M3I number(2,0), SG265AH number(2,0),
      H37B number(2,0), S903A number(2,0), V769A char(1), V770A number(2,0), HV243A number(2,0), V156 char(1), SHWH number(2,0), SG306 number(2,0), D103A number(2,0), HC63 number(4,0), V763B number(2,0), MM13 char(1), S325FB number(2,0), SG205 number(3,0), S574 number(3,0), M65B char(1), V716 number(3,0), D118XF char(1), HMLIDX2 number(2,0), SG255 number(3,0), SH123C number(2,0), ML18B char(1), SH619 number(2,0), SH246S number(6,0), D105N char(1), V167 char(1), S578O number(3,0), S579F number(5,0), D111 number(2,0), V743D number(2,0),
      SG267 number(2,0), SH8M number(3,0), SH9D number(3,0), V770O number(2,0), D1310B number(3,0), H1 number(2,0), H21 number(2,0), SH123B number(3,0), V746 char(1), SH217 number(5,0), SALLINCI number(2,0), V770S number(2,0), SIFUENTE4 number(6,0), V463E char(1), IDXH4 number(3,0), S435GC number(2,0), HML19 number(2,0), H44B char(1), S541H number(2,0), HML20 number(2,0), HV201 number(3,0), H32B number(2,0), SH71N number(7,0), HS109 number(2,0), HS110 number(2,0), V323 number(3,0), S435GN number(2,0), D106 number(2,0), S576B number(3,0), SH235A number(2,0),
      M65A char(1), V851L char(1), V852C char(1), V474X char(1), SHP4M number(3,0), HV104 number(2,0), SHP220B number(4,0), S540C number(2,0), ML19B char(1), ML20B char(1), HW9 number(6,0), SG269G number(2,0), V851H char(1), S568D number(2,0), V851G char(1), D105L char(1), H37X number(2,0), V781 char(1), SG270G number(2,0), HA2 number(5,0), M65C char(1), HV015 number(2,0), SH506 number(5,0), SG246Z number(2,0), SG206B number(6,0), M2E number(2,0), H12O number(2,0), M43 number(2,0), HV241 number(2,0), V751 number(2,0),
      S577H number(9,0), SG250 number(2,0), M65I char(1), S104A number(2,0), HV237H char(1), HC18 number(3,0), V305 char(1), SH242 number(2,0), SH227AF number(6,0), HML9 number(3,0), SG228H number(2,0), V463A char(1), V384B number(2,0), H46B char(1), SG123G number(2,0), SG249B number(7,0), HV232Y number(2,0), HV253F char(1), HB50 number(2,0), S937D number(2,0), V623 number(2,0), V452A char(1), V833C char(1), V452C number(2,0), HB61 number(2,0), V770W number(2,0), B9 number(2,0), V506 char(1), HV214 number(3,0), HA4 number(5,0),
      V762BV char(1), SG113C number(6,0), V3A08M number(2,0), SH0M number(3,0), SH1D number(3,0), SG108 number(3,0), HB12 number(6,0), S325CF number(2,0), S568A number(2,0), SG301G number(2,0), SH78O number(3,0), V479 char(1), V480 char(1), V3A00G number(2,0), HV111 char(1), S114D number(2,0), SGESTR char(1), SH110I number(2,0), IDXMCS number(3,0), H12W char(1), HML1A char(1), SH262 number(6,0), H32K number(2,0), S903B number(2,0), V3A00T char(1), SH6YZ number(2,0), SH136 number(2,0), V821B char(1), SG118B number(2,0), V155 number(2,0),
      HV215 number(3,0), D115XC char(1), SH225 number(3,0), HB62 char(6), HC70 number(5,0), S112B number(2,0), S435GI number(2,0), SG246C number(2,0), H39 number(2,0), H40 char(1), SH281 number(5,0), V854B char(1), V413 number(2,0), SG106 number(2,0), SHT3Y number(5,0), V372 number(2,0), HC72 number(5,0), V467C char(1), SG246A number(2,0), HV022 number(3,0), S1005 number(2,0), H4 number(2,0), V453 number(4,0), HC16 number(3,0), SHP4 number(2,0), D115C number(2,0), G117F char(1), S536C number(3,0), VCOL number(2,0), D118F number(2,0),
      D118U char(1), D119L number(2,0), SLNPM number(2,0), M55D number(2,0), HC56 number(4,0), D115Q number(2,0), D105G number(2,0), G100 number(2,0), SHP221AM number(3,0), M3L number(2,0), M61 number(4,0), SG301C number(2,0), SH33Y number(5,0), SHP221B number(4,0), ML13N char(1), SH242I number(4,0), V315 number(3,0), H37I number(2,0), V762AD char(1), H15A number(2,0), V770G number(2,0), V633F char(1), SHC0 number(3,0), V239 number(2,0), V240 number(3,0), V3A08AA char(1), HA61 char(1), HW55 number(2,0), V508 number(5,0), M72 number(3,0),
      V841A char(1), HV108 number(3,0), H32O number(2,0), SH96B number(6,0), SHRM5 number(6,0), SG217G number(2,0), SH243 number(3,0), SG273 number(2,0), ML17B char(1), S326C number(2,0), S435GX number(2,0), S583 number(3,0), S577M number(3,0), S578D number(3,0), D115XG char(1), HV035 number(2,0), SH221AM number(3,0), SGDIGIT number(3,0), S325FF number(2,0), HC6 number(6,0), HW16 number(3,0), SG222E number(2,0), V743E char(1), H32H number(2,0), S536B number(3,0), SG301D number(2,0), ML12 char(1), H35 char(1), H12F number(2,0), D110B number(2,0),
      M2L number(2,0), M3C number(2,0), M51 number(4,0), V472J char(1), V463C char(1), V473A char(1), H36B number(2,0), V414S number(2,0), V3A08C number(2,0), S325N number(2,0), S541F number(2,0), HA58 char(1), S523M number(2,0), SG201C number(2,0), SH220 number(4,0), ML17A number(2,0), SGINTA number(5,0), HV021 number(4,0), HV211 number(2,0), SH236 number(2,0), S949 number(2,0), S950 number(3,0), SG243B number(7,0), V105 char(1), SH5Y number(5,0), HW7 number(5,0), V762BW char(1), HV028 number(8,0), V463D char(1), SH95 number(6,0),
      HML10 number(2,0), M11 number(4,0), SHCOLD number(2,0), S435GD number(2,0), SG201K number(2,0), SG202B number(2,0), V621 number(2,0), H12X number(2,0), SH08 number(2,0), M65J char(1), HV125 char(1), V469F number(2,0), V766B char(1), V206 number(3,0), SG216C number(2,0), M7 number(3,0), V539 char(1), V540 char(1), V770N number(2,0), V762BX char(1), SG276 number(4,0), H15 number(2,0), M57O number(2,0), S572Y number(2,0), SG129 number(2,0), SHD4D number(3,0), SG272A number(2,0), H15K char(1), V3A00I number(2,0), V3A08K number(2,0),
      V3A09B char(1), CHL3 number(2,0), D105B number(2,0), SG266A number(2,0), HV234 char(1), S568B number(2,0), SG103 number(3,0), SH283M number(3,0), S541W number(2,0), SH6XB number(2,0), SG217D number(2,0), SH278 number(2,0), V770T number(2,0), H37C char(1), D119Y number(2,0), G117E char(1), M35 char(1), ML21B char(1), S570X number(2,0), V452B char(1), S568C number(2,0), SG247A number(2,0), G102 number(2,0), G117I char(1), SHRESI number(2,0), SG303C number(2,0), V407 char(1), V3A08W char(1), SG124 number(2,0), SH33M number(3,0),
      V205 number(2,0), HB67 number(3,0), SH6 number(2,0), SH139A number(3,0), M57S number(2,0), SH604 number(5,0), D118J number(2,0), D119A char(1), M34 number(4,0), V116 number(3,0), HV024 number(2,0), HV005 number(8,0), SG292A number(7,0), V310 char(1), HOVIDX number(3,0), SG213A number(2,0), V107 number(2,0), SH237 number(6,0), V744C number(2,0), SHRI number(5,0), SG228F number(2,0), M14 number(3,0), HC71 number(5,0), ML17C char(1), HC31 number(5,0), SH279A number(2,0), SH517 number(2,0), V770Q number(2,0), S536D number(3,0), H15D number(2,0),
      D118R number(2,0), V209 number(2,0), V210 number(2,0), D119I char(1), IDX94 number(2,0), V3A00Y number(2,0), S585 number(2,0), V783 char(1), HC55 number(2,0), SG228A number(2,0), V241 number(5,0), H8 number(2,0), S915 number(3,0), SH245 number(6,0), SGCONGL number(5,0), V505 char(1), H5 number(2,0), D101F number(2,0), SH75N number(7,0), H36D number(2,0), S523V number(2,0), V784R char(1), H32Z number(2,0), S576G number(5,0), D102 number(2,0), H9Y number(5,0), SG201G number(2,0), V745B char(1), H36E char(1), SG202L number(2,0),
      SH104B number(3,0), S435GJ number(2,0), V821A char(1), SG247D number(2,0), V151 number(2,0), SH235AE number(6,0), SH284B number(4,0), V512 number(3,0), SGVISITS number(2,0), SH18 number(2,0), HV002 number(4,0), HA64 char(1), SHMLIDX number(2,0), V3A00E number(2,0), M18 number(2,0), V125 char(1), V605 number(2,0), V3A08H number(2,0), D109 number(3,0), HB6 number(6,0), S523K number(2,0), M55A number(2,0), SH122A number(2,0), HV253H char(1), H12E number(2,0), SHH1Y number(5,0), V313 number(2,0), SHCOL3B number(3,0), SG216G number(2,0), HO108 number(2,0),
      ML18A number(2,0), H12T number(2,0), V364 number(2,0), V472M char(1), H15E number(2,0), HV252 number(2,0), SG253A number(4,0), S917 number(3,0), H12B number(2,0), V762AG char(1), D115P number(2,0), V482C char(1), V149 number(2,0), V150 number(3,0), V628 number(3,0), D113 number(2,0), SHH1D number(3,0), V135 number(2,0), SG201L number(2,0), SG202C number(2,0), V127 number(3,0), V401 number(2,0), V770B number(2,0), D105J char(1), V854A char(1), SG217X number(2,0), M2C number(2,0), HV232C number(2,0), SHP220 number(4,0), V784N char(1),
      GIDX number(2,0), HB64 number(2,0), HV117 number(2,0), SH197B number(3,0), S523W number(2,0), G116 char(1), V414M number(2,0), S937H number(2,0), B3 number(5,0), HV114 char(1)
    -> _All_
    -> BulkAttributeRenamer
_All_: Inspector
BulkAttributeRenamer
    PATTERN_ACTION_DISP = Change Case
    ATTRCHOICE = All Attributes
    CASE_CHANGE_TYPE = lowercase
    -> AttributeExposer
AttributeExposer
    ATTR_LIST = fme_feature_type
    -> AttributeCopier
AttributeCopier
    ATTR_LIST = fme_feature_type,tbname,
    -> StringReplacer
StringReplacer
    SRC_ATTRS = tbname
    REGEXP = no
    CASE = no
    FIND_TEXT = .
    REPLACE_TEXT = _
    NO_MATCH = _FME_NO_OP_
    -> Table1 (writer POSTGRES_1)
Table1 (writer POSTGRES_1) [off]
