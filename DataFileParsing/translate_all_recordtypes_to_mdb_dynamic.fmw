FME workspace translate_all_recordtypes_to_mdb_dynamic.fmw

Parameters:
- SourceDataset_CSV_6 = C:\Users\zool1301\Documents\DHS\Phase6\fmetest\*.csv   # Source CSV (CommaSeparatedValue) File(s)
- FEATURE_TYPES =
- DestDataset_MDB_ADO = C:\Users\zool1301\Documents\DHS\Phase6\fmetest\db\testsomefiles.mdb   # Destination Microsoft Access Database File
- SourceDataset_SCHEMA_FROM_TABLE = C:\Users\zool1301\Documents\DHS\Phase6\SurveySpecs\*.csv   # Source Dataset

Readers:
- CSV_4: CSV from $(SourceDataset_CSV_6)
- SCHEMA_FROM_TABLE_1: SCHEMA_FROM_TABLE from $(SourceDataset_SCHEMA_FROM_TABLE)

Writers:
- MDB_ADO_1: MDB_ADO to $(DestDataset_MDB_ADO)

CSV (reader CSV_4)
    attributes: CASEID text, V000 char(4), V001 number(3,0), V002 number(4,0), V003 number(3,0), V004 number(3,0), V005 number(7,0), V006 number(3,0), V007 number(5,0), V008 number(5,0), V009 number(3,0), V010 number(5,0), V011 number(5,0), V012 number(3,0), V013 number(2,0), V014 number(2,0), V015 number(2,0), V016 number(3,0), V017 number(5,0), V018 number(3,0), V019 number(3,0), V019A number(2,0), V020 number(2,0), V021 number(3,0), V022 number(3,0), V023 number(3,0), V024 number(2,0), V025 number(2,0), V026 number(2,0), V027 number(2,0),
      V028 number(4,0), V029 number(2,0), V030 number(3,0), V031 number(3,0), V032 number(2,0), V034 number(3,0), V040 number(3,0), V042 number(2,0), V044 char(1), G117B char(1), V784X text, S326AB number(2,0), V763A number(2,0), S114E number(2,0), ML13F text, V504 number(2,0), SH263 number(2,0), V851E char(1), V3A08R number(2,0), SH130CB number(2,0), V851A char(1), M65L char(1), S715D number(2,0), D118T number(2,0), D119K number(2,0), D118XC char(1), V784L text, B7 text, S539 number(2,0), V845 char(1),
      HV003 text, S715ABC number(2,0), S1209C number(2,0), ML22A char(1), V704 text, M57M text, V767A text, S715ABF number(2,0), MMC3 char(1), D103F char(1), V472E char(1), SQLANG number(2,0), D105H number(2,0), V414J text, HV208 number(2,0), H11B text, S114 number(3,0), V474G char(1), SH284 number(4,0), S715F number(2,0), V471C char(1), HW53 text, V414Q char(1), S112H number(2,0), S1203 number(2,0), D112N char(1), M42E text, SH1X number(2,0), HC60 number(4,0), V481A text,
      V326 number(3,0), V802 number(5,0), HV212 text, S507D number(2,0), SH246D number(4,0), HV001 text, H12I text, H32Q char(1), S523U number(2,0), H33Y text, V224 text, M42A char(1), S506A text, V218 text, SH130CA number(2,0), S325J number(2,0), V161 number(3,0), SH244 number(2,0), V215 text, V509 number(5,0), V510 number(2,0), S435GE number(2,0), M57C char(1), V414B char(1), SH284A number(4,0), HB5 text, S325M number(2,0), HML3 number(2,0), HC13 text, H40M char(1),
      HC61 number(2,0), V231 text, HW3 text, V768B char(1), SH17B number(3,0), H6 text, S538P number(2,0), S540G number(2,0), ML13Y number(2,0), MM1 number(2,0), S540D number(2,0), HV246F text, HV105 number(3,0), V474J char(1), HA52 number(2,0), S325FH number(2,0), V743A number(2,0), S435E number(2,0), HB2 text, V302 char(1), ML18C char(1), M2A number(2,0), M38 text, S433L number(2,0), V3A08O char(1), H32C number(2,0), V232 text, SH230 number(3,0), SH20K number(3,0), ML19F char(1),
      S540K number(2,0), S541B number(2,0), HV031 text, S325FD number(2,0), V843 text, S506YM number(3,0), SH20D number(2,0), H6Y text, V461 text, HV129 char(1), V3A08P number(2,0), V714 number(2,0), HV243D text, B1 number(3,0), S325D number(2,0), SPROV number(2,0), D118E number(2,0), HB13 text, SH110J number(2,0), HV121 text, SH111A number(3,0), M1C char(1), M8 text, ML14Z char(1), D115O number(2,0), S1016 number(2,0), D100A number(2,0), S541D number(2,0), M55Z text, M57H text,
      M2I text, M47 char(1), G117J char(1), V414A char(1), HC33 number(2,0), M3G text, S111E number(2,0), V225 text, HC7 text, MM3 number(3,0), M2M text, M3D text, M52 text, S112A number(2,0), S541V number(2,0), SH19 number(2,0), SH20 number(2,0), D119XH char(1), HV247 number(2,0), HML12 text, V538 char(1), S714BB number(2,0), S325FZ number(2,0), HML32A text, S1015 number(2,0), V467E char(1), M57D char(1), V770P text, V472Q char(1), S715ABI number(2,0),
      V778 text, V478 text, V754CP number(2,0), SH232 number(2,0), S540J number(2,0), M42C text, S541A number(2,0), HB41 text, V166 text, V744A number(2,0), V463B text, V770X number(2,0), SH110H number(2,0), S523P number(2,0), SH110G number(2,0), V762AJ text, V762BA text, S501 number(2,0), HV041 text, D103E char(1), SHRM4 number(6,0), S435GB number(2,0), HV204 number(4,0), V121 number(2,0), AWFACTW text, M6 text, SH2M number(3,0), V472S char(1), V474A char(1), SH3D number(3,0),
      HV253D char(1), G103 number(2,0), ML16C char(1), H32D number(2,0), S523F number(2,0), HML32F text, D120 number(3,0), V228 text, HV115 text, D123 char(1), M19A text, D119XE char(1), SH17A number(2,0), S906A number(2,0), V233 text, V3A00L number(2,0), V537 number(3,0), HB12A text, D118XI char(1), G124 number(3,0), SH283T number(5,0), HV232B text, S523T number(2,0), HV243B text, SH118F number(2,0), D115H char(1), V784Q char(1), M49E text, D118XD char(1), M2G number(2,0),
      M45 text, HB1 number(3,0), D115R number(2,0), HV012 number(3,0), V104 char(1), SH20I number(3,0), HV017 number(2,0), S538O number(2,0), S540F number(2,0), HV235 number(2,0), V379 char(1), V380 char(1), V413A char(1), HV027 text, V3A00Z number(2,0), V762AK text, V762BB text, S804 number(2,0), H4M text, H5D text, V851B char(1), HW72 text, H37K text, S229C number(2,0), V844 char(1), HV019 text, HV020 number(2,0), S509B number(2,0), S510B number(2,0), V770I text,
      D119XI char(1), S502C number(2,0), H0M text, D118XH char(1), ML13G char(1), D118W number(2,0), D119N number(2,0), M49X text, V212 text, HV226 number(3,0), HA57 number(2,0), SHHTEC number(4,0), V784K text, V474 char(1), H12H text, V412A text, M15 text, ML13H number(2,0), ML15C char(1), V481C text, V614 number(2,0), V3A08Z number(2,0), H37O text, S504C number(2,0), HC62 text, HB55 text, HB66 number(2,0), HA53 number(4,0), S540X number(2,0), S541O number(2,0),
      SHB2M number(3,0), V119 number(2,0), V120 number(2,0), SHB3D number(3,0), SHB1Y number(5,0), S1309C2 number(2,0), V158 text, S541M number(2,0), SH218F number(2,0), V853C char(1), V316 number(5,0), S906B number(2,0), V204 number(2,0), M57U char(1), D103B number(2,0), HV014 number(2,0), H32L number(2,0), D117 char(1), M3K text, M60 text, HW18 number(3,0), S326 number(2,0), HC5 text, V375A char(1), V851K char(1), M65K char(1), V852B text, D101C number(2,0), ML19E char(1), HV228 text,
      HA11 number(5,0), V633G char(1), H2Y text, ML19Z char(1), V471D char(1), V465 text, V376 text, V471E char(1), V775 char(1), HMLIDX number(2,0), S540H number(2,0), S541S number(2,0), D110H char(1), HC73 text, S523I number(2,0), HV242 text, S540L number(2,0), S541C number(2,0), V627 number(3,0), D110F char(1), SH221 number(3,0), HA12A number(6,0), D118H char(1), ML13C text, H7Y text, ML0 number(2,0), V770C number(2,0), G113 char(1), V472A char(1), S945O number(2,0),
      V625A number(2,0), V762AI char(1), V762AR char(1), V307 number(2,0), V762BI char(1), HV238 number(3,0), D115XE char(1), V322 number(2,0), G117D char(1), V743F text, HV253A text, SHSMK char(1), S435GM number(2,0), H12C text, HB4 text, HA3 number(5,0), M65E char(1), M71 text, B12 text, SH283Y number(5,0), SH1H number(3,0), D115XI char(1), H12D text, S407B number(2,0), V237 number(2,0), V855 text, HV227 text, V770J text, V219 text, V220 number(2,0),
      ML2 number(2,0), V438 text, V815C text, M57J text, S502E number(2,0), SH2011 char(1), V616 number(4,0), H37J text, D118A char(1), V820 char(1), H12U text, MM12 char(1), S1202 number(2,0), S541G number(2,0), V414I text, V367 number(2,0), SH218B number(2,0), HV113 text, V761C char(1), V774C number(2,0), SH231 number(2,0), D105K char(1), V762AX text, V762BO char(1), V238 number(2,0), D116 number(3,0), S229B number(2,0), V3A00R char(1), HV237B text, SH242C number(2,0),
      V3A08S number(2,0), SHPC1 number(5,0), H32E number(2,0), S111 number(2,0), V131 text, M49B text, H15I text, ML13A number(2,0), SHPROV number(2,0), G114 char(1), V603 number(4,0), S223B number(2,0), HV253Z text, V812 text, V412C text, G123 number(2,0), V321 number(2,0), HW58 char(1), HV253E char(1), SHSD1 number(5,0), SHRM1 number(6,0), HV237F text, V304 text, M57P text, V3A08AB char(1), HV008 number(5,0), H3M text, H4D text, SHB1M number(3,0), V604 number(2,0),
      SHB2D number(3,0), D124 char(1), ML13K number(2,0), ML14B char(1), D119XJ char(1), V3A08AD char(1), S506B number(2,0), V784I char(1), S937A number(2,0), V129 number(3,0), V130 text, D118M number(2,0), V472T char(1), M55E text, V474B char(1), H38 text, HV030 number(3,0), S1401E number(2,0), S715ABJ number(2,0), D119D number(2,0), V471B char(1), V629 number(3,0), V838B text, S326AC number(2,0), MM10 char(1), V770R text, V3A08X number(2,0), V784V char(1), HV230A text, S523L number(2,0),
      D119V number(2,0), S210 number(2,0), V203 number(2,0), V784A text, SH249 number(2,0), SH250 number(2,0), SH248 number(2,0), H31 text, V152 number(3,0), IDX95 number(2,0), V841 text, D115I char(1), FDYSTO number(4,0), SH130CZ number(2,0), H41B char(1), H15L char(1), H2D text, H42 text, V414T char(1), HV246C text, SH21 number(2,0), ML13J number(2,0), ML14A char(1), HW6 text, S502B number(2,0), MM7 number(3,0), HML14 text, B8 text, H8M text, H9D text,
      S435D number(2,0), H37F char(1), S715ABH number(2,0), M1B char(1), M29 text, D119XD char(1), SH08A number(2,0), V3A08Q number(2,0), V827 char(1), H9M text, HW12 text, S325CH number(2,0), S507A number(2,0), V477 text, V625 number(2,0), H15M char(1), M4 text, M13 text, V463F char(1), HV216 number(3,0), HB0 number(3,0), V103 char(1), S1001 number(2,0), S506I1Y number(5,0), V825 text, S506I2M number(3,0), D101B number(2,0), V847 char(1), SH14 number(2,0), H32G text,
      V714A number(2,0), S112F number(2,0), SH3M number(3,0), HV244 number(2,0), V472D char(1), V822 text, ML21C char(1), H2M text, H3D text, M1 text, S504E number(2,0), HV246I text, H15G text, H9 text, HV102 number(2,0), V739 number(2,0), V740 char(1), SH110O number(2,0), HV009 number(3,0), HV010 number(2,0), HML18 text, V839A text, V840A text, IDXML number(2,0), V235 text, ML13L number(2,0), V762AS text, M57I text, M49G char(1), V762BJ text,
      HV219 number(2,0), HV220 number(3,0), SH110L number(2,0), SH218E number(4,0), HV253B text, HV253 text, M55J text, D110E char(1), V3A05 text, D101G number(2,0), V823 number(2,0), HML7 number(3,0), V842 text, D110A number(2,0), V408 char(1), S937B number(2,0), HV140 text, D115Y number(2,0), V784U char(1), S506F number(2,0), S504X number(2,0), M10 text, V838C text, V409 text, V410 text, HV011 text, D118XG char(1), HA67 text, V467K char(1), V743B number(2,0),
      HVIDX number(3,0), HML1 text, S506AY number(5,0), V835B char(1), SH118A number(2,0), S714E number(2,0), D115N number(2,0), D105F number(2,0), D129 char(1), S114GX number(3,0), V824 text, V395 text, V405 text, V851C char(1), HML33A number(3,0), D121 number(2,0), S111A number(2,0), SH130B number(2,0), SH130CX number(2,0), V535 number(2,0), V216 text, HB11 text, V850A text, S325O number(2,0), D118I char(1), S326AX number(2,0), D119S number(2,0), D122A number(2,0), SHB3 number(2,0), V829 text,
      H14 text, H12P text, V830 char(1), H32I text, SH273 number(5,0), AWFACTU text, HMLC number(3,0), HV237K char(1), M39A text, V633A char(1), S523B number(2,0), SH118B number(2,0), HA50 text, V3A08AC char(1), V536 number(2,0), S541R number(2,0), V762AN text, V762BE text, HV116 text, HML32G text, M55K text, V3A08B number(2,0), M65D char(1), MMC4 char(1), S105 number(2,0), HV236 char(1), H8Y text, H12J text, S435GK number(2,0), SH284G number(4,0),
      S111D number(2,0), G106 number(3,0), B10 number(2,0), V217 text, V472N char(1), D118P number(2,0), V527 number(4,0), D119G number(2,0), V784B text, SINTERP number(2,0), D101J char(1), V784C text, HA35 text, SHBM number(5,0), SH3 number(14,0), H12Z text, D125 char(1), V472U char(1), V474C char(1), S523S number(2,0), HC32 number(5,0), V376A char(1), HV013 number(3,0), HV237E text, SHDISTRICT number(2,0), V414F text, H4Y text, S502A number(2,0), HV209 number(2,0), HV210 number(2,0),
      HB58 char(1), S715B number(2,0), D101H char(1), SH1Y number(5,0), ML13P char(1), V472R char(1), BORD text, SH238 number(2,0), V631 char(1), S714D number(2,0), S28DAYS number(2,0), H37G char(1), D105C number(2,0), ML15B char(1), S508 number(2,0), V762BU text, S540E number(2,0), H37A text, HV218 number(2,0), SH234C number(3,0), MM14 number(3,0), S503A number(2,0), HC52 number(2,0), HB3 text, V624 text, V762AC text, MMC1 number(3,0), S114B number(2,0), SH2X number(2,0), H5Y text,
      G117H char(1), M27 text, M65X char(1), HC12 text, V472G char(1), V415 text, S1401F number(2,0), S1205 number(2,0), H43 text, S435H number(4,0), V719 number(2,0), V454 text, B2 number(5,0), S435GF number(2,0), ML24C char(1), H3Y text, V761B text, S111B number(2,0), H12G text, HV118 text, ML13Z number(2,0), S1004 number(2,0), H7 text, HW51 text, H32J number(2,0), SHB13 char(1), V3A08L number(2,0), V613 number(3,0), V414W text, ML19A char(1),
      ML20A number(2,0), SHRM3 number(6,0), SHSD3 number(5,0), V468 number(2,0), V234 text, V836 text, HB32 number(5,0), G119 number(2,0), V3A01 char(1), HC11 text, M55C text, HA33 number(2,0), MM11 char(1), V412B char(1), HA6 number(6,0), HA41 number(5,0), H2 text, V3A08G number(2,0), D107 number(2,0), V472H char(1), V784S char(1), V528 number(3,0), V325A char(1), V832C char(1), V853B text, MM8 number(5,0), D110C number(2,0), SH20H number(2,0), V467M char(1), V732 number(2,0),
      HV253G char(1), B4 number(2,0), HV230B text, HB40 text, D118XK char(1), V763C number(2,0), SH215A number(2,0), V767C char(1), V419 number(2,0), V420 char(1), ML101 text, S326AA number(2,0), HV246J char(1), HB63 text, S541X number(2,0), M70 text, S509C number(2,0), S510C number(2,0), S502F number(2,0), G112 char(1), M36 char(1), D115K number(2,0), M42B char(1), V762AF char(1), V744D number(2,0), SH127A number(2,0), B5 number(2,0), S522D number(2,0), V467L char(1), V851F char(1),
      HW17 number(3,0), H20 text, S503D number(2,0), M3M text, M62 text, V157 text, V359 number(3,0), V360 number(3,0), V834C char(1), HV000 char(4), H36A text, HV246H text, HC8 text, V762AP char(1), V762BG char(1), HA62 text, D105E number(2,0), V481F char(1), D127 char(1), S506E number(2,0), H12S text, V469E text, V851D char(1), S715ABG number(2,0), V815A text, V762AH char(1), SH130A number(2,0), V302A number(2,0), H12Y text, M55I text,
      V414P text, S507X char(1), M57N text, S509F number(2,0), S510F number(2,0), M49Z text, V446 text, V3A00K number(2,0), HV239 char(1), HV240 char(1), HB35 text, V413D char(1), V784O text, M57L text, H6M text, H7D text, V418 number(2,0), S506AD number(3,0), HV213 number(3,0), V211 text, V311 char(1), V784F text, V472K char(1), V473B text, S325CB number(2,0), HA5 number(5,0), M55L char(1), S507C number(2,0), V848 char(1), ML23A text,
      V122 number(2,0), D101E number(2,0), HW52 text, HML31 text, ML13X number(2,0), V414H text, VCAL text, S540I number(2,0), V805 text, M2B number(2,0), M39 text, G117Y char(1), HMLD number(3,0), D119T number(2,0), D122B number(2,0), H15C text, V750 number(2,0), D118C number(2,0), V754JP number(2,0), SH1M number(3,0), SH2D number(3,0), H37M text, V849 char(1), HB51 text, V754BP char(1), M1D text, M57T text, V846 char(1), D118XJ char(1), M57A text,
      V770D number(2,0), V134 text, SH3H number(3,0), G109 char(1), G110 char(1), HML32B text, S523R number(2,0), D118Y number(2,0), D119P number(2,0), S325FX number(2,0), SH3X number(2,0), H32T number(2,0), S510J number(2,0), V3A00F text, S504B number(2,0), HA69 text, HA70 text, V853A text, G111 char(1), D119XG char(1), H41A char(1), D119W number(2,0), V409A char(1), V410A char(1), MMC5 number(3,0), D115B number(2,0), V471F char(1), V437 text, H32F text, HV023 text,
      HV101 number(3,0), ML19D char(1), SH279 number(2,0), SH280 number(5,0), S509A number(2,0), V242 text, D110D char(1), S510A number(2,0), S523D number(2,0), HV040 text, HML30 text, V414V text, V463X text, V472C char(1), S509E number(2,0), S510E number(2,0), H37N text, S435F number(2,0), G117X char(1), M55X text, M57F text, V769 text, V770 number(2,0), V3A02 text, S715AA number(2,0), V3A00H text, V202 number(2,0), M2K number(2,0), M55M char(1), V141 text,
      M3B text, M50 text, V323A number(3,0), V414E text, S439A number(3,0), SH259 number(2,0), V462 char(1), SH260 number(2,0), HA1 number(3,0), V837 char(1), V213 number(2,0), V458 char(1), ML22B char(1), S435GG number(2,0), H37Z text, S509D number(2,0), S510D number(2,0), HV106 number(2,0), V701 number(2,0), V633B text, V439 text, V440 text, V602 number(2,0), HB53 text, D103D char(1), V634 char(1), V784D text, HV232D text, HV237 text, V312 number(3,0),
      S506I1M number(3,0), S1209H number(2,0), HA56 number(4,0), S506I2D number(3,0), ML22C char(1), D118L number(2,0), D119C number(2,0), ML13D number(2,0), H36F char(1), HML17 text, MMIDX number(3,0), V774B number(2,0), HML2 text, D100D number(2,0), H31C text, S715C number(2,0), V502 number(2,0), SH1MO number(3,0), D105A number(2,0), B11 text, V833B text, M49Y text, HC51 number(3,0), M55G text, H10 text, ML13M number(2,0), V803 number(3,0), M57R text, HC19 number(5,0), D115XJ char(1),
      ML16A number(2,0), V384A number(2,0), S1401A number(2,0), V756 number(2,0), M73 text, S114C number(2,0), D115G number(2,0), M65H char(1), V413B char(1), HML11 number(2,0), V754DP number(2,0), V768C char(1), HV109 number(2,0), HW10 text, HV110 char(1), SHED3 number(2,0), V745A text, G117C char(1), S505 number(2,0), V3A00P char(1), V337 number(3,0), V784H char(1), V761 text, V784J char(1), V762AE text, HV246 number(2,0), HV237X text, V411A text, V839 text, V840 text,
      M3H text, V457 text, V472O char(1), V762AV text, V762BM text, HV122 text, HV225 number(2,0), HW70 text, HV127 char(1), M5 text, SH1 number(14,0), V153 number(2,0), V472L char(1), HB52 text, MM5 char(1), V814 text, H0D text, H22 number(2,0), SHCMC number(4,0), S435GL number(2,0), V159 text, V160 number(2,0), ML13E number(2,0), S306A number(2,0), M2F text, M44 char(1), HV007 number(5,0), SH3Y number(5,0), V633E char(1), V762AO char(1),
      M57V char(1), V762BF char(1), SH15 number(2,0), V414C char(1), D118V number(2,0), D119M number(2,0), HML32D text, HA65 number(2,0), S715AD number(2,0), V102 number(2,0), V762BZ text, SH258 number(2,0), S114G number(2,0), H37L text, S509Z number(2,0), S510Z number(2,0), V762AQ char(1), V762BH char(1), SH271 number(5,0), V3A00N number(2,0), H32X number(2,0), D118X number(2,0), S823B number(2,0), HC17 number(3,0), S1209G number(2,0), SH122C number(5,2), S506I1D number(3,0), D119O number(2,0), V124 number(2,0), V482B char(1),
      HV207 number(2,0), D130A char(1), HV044 text, H37D text, V467G char(1), V414D char(1), V3A00J number(2,0), V731 number(2,0), V3A08N number(2,0), HW8 text, ML1 text, HB56 text, BIDX text, H12K text, H13B text, V762AW char(1), V762BN text, V763E char(1), V137 number(2,0), S325A number(2,0), S541Y number(2,0), V138 number(2,0), HV246G text, D119XA number(2,0), V128 number(3,0), S536K number(2,0), HML5 text, V476 char(1), V207 number(2,0), REC84_GROUP char(1),
      G121 number(2,0), G107 number(3,0), HC58 char(1), S502Z number(2,0), D115S number(2,0), D117A number(2,0), HIDX number(2,0), HMLB number(3,0), S325CX number(2,0), HV103 number(2,0), M49A text, H12L text, HV246A text, HV221 number(2,0), HV246E text, HV237C text, V784T text, V744B number(2,0), S5YEARS number(2,0), V3A08A text, S325CE number(2,0), HC53 number(4,0), HMLA number(3,0), V447A text, V3A04 text, V414R char(1), S541E number(2,0), V784E text, V3A08F number(2,0), S103A number(2,0),
      H32A number(2,0), V227 text, H32P text, V768A char(1), V481B text, V813 text, SH2MO number(3,0), S616 number(3,0), M49C text, HML34 text, G101 number(2,0), B13 text, V762AM text, V762BD text, V541 char(1), V481D text, V762AA text, SHB1D number(3,0), HC3 text, SH255D number(4,0), SH257 number(2,0), FSYSTO number(4,0), HB60 text, HB68 number(2,0), S502G number(2,0), V832B text, S507B number(2,0), S540W number(2,0), S541N number(2,0), S506C number(2,0),
      V811 text, V406 text, HML16A number(3,0), S714BC number(2,0), G118 number(2,0), D119X number(2,0), D118Q number(2,0), D119H char(1), S1209E number(2,0), V474D char(1), M55O char(1), S504Z number(2,0), S506H number(2,0), S541L number(2,0), V466 char(1), V784P char(1), H12R char(1), M3J text, HML16 text, HV128 char(1), HW5 text, V414K text, V715 number(3,0), V770V text, S506Z number(2,0), S504D number(2,0), MIDX number(2,0), D130B char(1), V444A text, D103C char(1),
      H31E text, S715ABE number(2,0), D115E number(2,0), SH110K number(2,0), SH111B number(2,0), S509X number(2,0), S510X number(2,0), V3A00C number(2,0), S325FA number(2,0), ML19X char(1), SH242B number(2,0), SHADULT35 number(2,0), SH20E number(3,0), D114 number(2,0), SHED1 number(2,0), V529 number(4,0), V530 number(2,0), V511 number(3,0), SH16 number(3,0), V770L number(2,0), SH218G number(3,0), V413C char(1), SH255S number(4,0), S523G number(2,0), V503 number(2,0), S325CG number(2,0), H15H text, SHUPAZILA number(3,0), V3A00Q char(1), V763G char(1),
      D101D number(2,0), M57Q text, V774A number(2,0), V3A06 text, V481E char(1), H12V text, D115XF char(1), SCONCES number(4,0), AWFACTT text, H32U number(2,0), V834B text, S541Q number(2,0), SH2 number(14,0), M42D text, S506D number(2,0), HC1 number(3,0), V826A text, H3 text, S541K number(2,0), V463G char(1), V3A00D number(2,0), D118S number(2,0), D119J number(2,0), D121A number(2,0), S522C number(2,0), SH209A number(2,0), AWFACTE2 number(5,0), HV206 number(2,0), SH123A number(2,0), D005 number(8,0),
      D119XK char(1), H7M text, V3A00S number(2,0), M57X text, H8D text, V741 number(2,0), M17 text, V779 text, V780 text, MM15 char(1), D105D number(2,0), V464 text, MMC2 number(3,0), REC31_GROUP text, V414N text, V3A03 text, SH234 number(3,0), HML15 text, ML13O char(1), V507 number(3,0), SH283 number(9,0), H15B text, G117A char(1), G104 number(2,0), D110G char(1), H31D text, SH283D number(3,0), D108 number(2,0), V3A00W text, V762AB text,
      HV245 number(4,0), S604A number(3,0), D101I char(1), S504A number(2,0), V838A text, HV237Z text, D115W number(2,0), H37E text, V482A char(1), H13 text, HA13 number(2,0), SH264D number(4,0), SH242A number(2,0), SH130CE number(2,0), V762AT text, V762BK text, M55H text, G108 number(3,0), H0 text, V474E char(1), HV026 text, SH20J number(2,0), SH228 number(2,0), M55B text, SHB2Y number(5,0), D115L number(2,0), V481H char(1), V455 text, G115 char(1), G122 number(3,0),
      HV004 text, S715AC number(2,0), D118D number(2,0), V763F char(1), SCOMM number(3,0), V190 number(2,0), S506G number(2,0), D105I number(2,0), D118B number(2,0), S435GA number(2,0), S325CC number(2,0), SHB3M number(3,0), M55N char(1), V744E number(2,0), HA12 number(6,0), HB57 text, V3A00V number(2,0), S106 number(3,0), S541I number(2,0), V372A text, V106 number(2,0), H0Y text, H45 char(1), HV202 char(1), S714F number(2,0), M2D text, SHB1 number(2,0), V363 text, M2N number(2,0), M3E text,
      D118XB char(1), HML32E text, M49F text, SH253 number(5,0), D100B number(2,0), HV234A text, HA54 number(2,0), HV107 number(2,0), V3A08J number(2,0), V3A09A char(1), HV246D text, ML11 char(1), V474H char(1), V208 number(2,0), S435C number(2,0), S1206 number(2,0), HW13 number(2,0), HV018 text, V763D char(1), AWFACTE text, V632 number(2,0), V412 char(1), ML14Y char(1), V467H char(1), SH241 number(2,0), V472P char(1), HV032 number(2,0), HV237I char(1), HA55 number(2,0), V3A08V number(2,0),
      V3A00A number(2,0), D119XB char(1), V3A08D number(2,0), HA0 number(3,0), V243 text, D115J number(2,0), SH104A number(2,0), HW56 text, HV016 number(3,0), ML16B char(1), H37H text, V414U char(1), S1209A number(2,0), S541P number(2,0), D1310A number(2,0), HC68 number(2,0), SHB3Y number(5,0), S506YY number(5,0), ML19C char(1), ML20C char(1), H5M text, H6D text, S1013 number(2,0), HV253X text, H32Y number(2,0), M65G char(1), D115U char(1), V3A08E number(2,0), ML19Y char(1), HW71 text,
      HMHIDX text, S325CZ number(2,0), S540A number(2,0), S435J number(2,0), S229A number(2,0), S325CA number(2,0), S503C number(2,0), V3A07 number(3,0), V469X text, V472F char(1), AWFACTR text, V702 number(2,0), HC10 text, V417 number(2,0), V834A text, HV006 number(3,0), H44C char(1), D119Q number(2,0), V474F char(1), SH2H number(3,0), V851I char(1), V626 text, HA63 text, S523J number(2,0), D105M char(1), HV243C text, SCORE number(3,0), D115T number(2,0), B16 number(3,0), H12M text,
      S506AM number(3,0), D115XD char(1), HV246B text, SHFLG number(2,0), D118N number(2,0), HV270 number(2,0), D119E number(2,0), S410J number(2,0), M57B text, V362 number(2,0), V3A08T number(2,0), M2H number(2,0), M46 text, V319 number(2,0), V705 text, V320 number(2,0), HW2 text, V826 char(1), S823A number(2,0), M3F text, M54 text, V301 text, M49D text, S714BA number(2,0), V762BS text, V717 text, V785 number(2,0), HB33 number(2,0), S1208 number(2,0), M9 text,
      SH110N number(2,0), S715ABK number(2,0), H34 text, HML21 number(2,0), V472I char(1), D115XA number(2,0), HW57 text, V770F number(2,0), M19 text, SH212A number(4,0), S503Z number(2,0), D115XB char(1), V721 char(1), V421 char(1), V318 number(2,0), D119U char(1), D122C number(2,0), SH239 number(3,0), MM6 number(3,0), V766A text, HML6 number(2,0), D104 number(2,0), HA32 number(5,0), ML15A char(1), SH20A number(2,0), V467A char(1), SH19A number(2,0), ML23B char(1), HA60 text, S435GZ number(2,0),
      HV042 text, V828 text, HV124 text, V445 text, MM2 number(2,0), H36C text, HC27 number(2,0), HV237D text, V113 number(3,0), S1401G number(2,0), S714C number(2,0), D115XH char(1), V123 number(2,0), HML8 number(2,0), V393 text, HMLE text, S714AA number(2,0), V136 number(3,0), S435GH number(2,0), S1002 number(2,0), V532 number(2,0), S325B number(2,0), V833A text, HHID text, MM4 number(5,0), S523O number(2,0), V447 text, V475 char(1), S523A number(2,0), D118XE char(1),
      HC15 text, ML13B number(2,0), M1A text, M28 text, HC0 number(3,0), V115 number(4,0), S523N number(2,0), D115M number(2,0), H21A text, V139 number(3,0), V140 number(2,0), H32V text, H33M text, H40D char(1), V501 number(2,0), S523C number(2,0), HV237A text, B15 number(2,0), S1209F number(2,0), M1E text, HML32 number(2,0), SHCOLL number(3,0), S540B number(2,0), HA66 number(2,0), H32N number(2,0), S541J number(2,0), V471G char(1), V443 text, S223A number(2,0), S326B number(3,0),
      HC2 text, V801 number(5,0), AWFACTE3 number(5,0), HB65 number(2,0), V474I char(1), S541T number(2,0), D119R number(2,0), S506X number(2,0), V777 text, V411 text, ML21A text, HV123 text, HV237G text, D128 char(1), H40Y char(1), H37Y text, S435I number(2,0), S325CD number(2,0), MLWEIGHT char(1), D119XF char(1), SH276 number(2,0), V467B text, V831 char(1), HV217 number(2,0), D112A number(2,0), S823 number(2,0), HV025 number(2,0), S523E number(2,0), H32R char(1), V414G text,
      HWIDX number(2,0), V762BR char(1), D101A number(2,0), V463Z text, V101 number(2,0), HML35 text, V414L text, D115V number(2,0), H31B text, HW15 text, V626A text, V394 text, V404 text, V384C number(2,0), S503F number(2,0), SHB2 number(2,0), V531 number(3,0), V317 number(5,0), V471A char(1), HA40 number(5,0), M57G text, S325FE number(2,0), SH254 number(2,0), H44A text, HV232 text, S111C number(2,0), S503B number(2,0), V416 text, S1207 number(3,0), V456 text,
      HML32C text, V815B text, M2J char(1), M3A text, M48 char(1), HW4 text, S1003 number(2,0), HV126 char(1), HV253C text, V467D text, HV205 number(3,0), S805 number(2,0), V444 text, HA68 number(2,0), HV246K char(1), S803A number(2,0), S715ABX number(2,0), V472B char(1), ML23C char(1), V835C char(1), SH264S number(4,0), V762AU text, V762BL text, SH20F number(2,0), HV120 number(2,0), V525 number(3,0), H32S number(2,0), B0 number(2,0), V762BT text, V770K text,
      V3A00X number(2,0), V223 number(2,0), V770U number(2,0), V767B text, SHED2 number(3,0), V3A08I number(2,0), D115X number(2,0), S307 number(3,0), V743C char(1), HML33 text, S114F number(2,0), S715A number(2,0), S1211 char(1), V513 number(2,0), S1014 number(2,0), V442 text, HW11 text, SH13 number(2,0), V804 number(2,0), D115D number(2,0), H37P text, S523Q number(2,0), V441 text, HV232E char(1), V3A00B number(2,0), HB69 text, HB70 text, HV237J char(1), H32M number(2,0), H33D text,
      D115F number(2,0), D100C number(2,0), G105 number(2,0), M65F char(1), MM9 number(3,0), V229 text, V230 text, HC30 number(3,0), D118O number(2,0), D119F number(2,0), D112 number(2,0), S519J number(2,0), HML4 number(3,0), HB12B text, V762AZ text, V762BQ char(1), V770M number(2,0), S112E number(2,0), V226 text, V481X text, H15F text, D118XA number(2,0), V784M text, HA12B number(6,0), V835A char(1), HW1 number(3,0), V3A00U number(2,0), M57E text, M57K text, B6 text,
      M55F text, G117G char(1), HC9 text, S114A number(2,0), H12A text, HML13 text, V754WP number(2,0), M66 text, S112C number(2,0), ML13I number(2,0), V806 text, V221 text, V770E number(2,0), SILANG number(2,0), V3A00O text, S503E number(2,0), H47 text, V851J char(1), V852A text, V821C char(1), V168 text, V133 number(3,0), V191 text, V201 number(3,0), V3A08U number(2,0), H46A number(3,0), V414O text, H11 text, V304A text, V762AL text,
      V762BC text, SH235 number(2,0), HV112 text, S715ABB number(2,0), V214 number(2,0), V729 number(2,0), V730 number(3,0), H12N text, V467F text, D119XC char(1), H32W text, V474Z char(1), HC64 number(3,0), V426 text, HW73 text, S536A number(2,0), V327 number(2,0), V784G char(1), S325E number(2,0), D118K number(2,0), S1209X number(2,0), S523X number(2,0), V361 number(2,0), SH2Y number(5,0), D118G number(2,0), D119B number(2,0), HV271 text, V481G char(1), V222 text, D115XK char(1),
      SH22 number(2,0), HC57 number(2,0), S502D number(2,0), S523H number(2,0), V467J char(1), SH218A number(2,0), V770H text, V467I char(1), S945A number(2,0), V459 text, V460 text, S325FC number(2,0), HC4 text, H33 text, HW19 number(5,0), S541U number(2,0), H15J char(1), S229D number(3,0), V481 text, V633C char(1), H12Q char(1), V850B text, SH3MO number(3,0), V633D char(1), V762BP char(1), S1401B number(2,0), V3A00M number(2,0), HA51 text, M3N text, M3I text,
      S1012 number(2,0), H37B text, D126 char(1), HV243A number(2,0), V769A text, V770A number(2,0), S502H number(2,0), V156 char(1), SHWH number(2,0), HC63 number(4,0), D103A number(2,0), V763B number(2,0), S325FB number(2,0), MM13 char(1), M65B char(1), V716 text, D118XF char(1), ML18B char(1), SH246S number(4,0), D105N char(1), V167 text, S507Z char(1), D111 number(2,0), V743D number(2,0), V770O number(2,0), D1310B number(3,0), H1 text, H21 text, SH110M number(2,0), V746 text,
      S309A number(2,0), S1201 number(2,0), V770S text, V463E char(1), IDXH4 number(3,0), S435GC number(2,0), HML19 text, H44B char(1), S541H number(2,0), S715ABA number(2,0), HML20 text, HV201 number(3,0), H32B number(2,0), V323 number(3,0), S435GN number(2,0), D106 number(2,0), M65A char(1), V851L char(1), V852C char(1), V474X char(1), HV104 number(2,0), ML19B char(1), ML20B char(1), S540C number(2,0), HW9 text, SCOLL number(3,0), V851H char(1), D105L char(1), V851G char(1), H37X text,
      V781 text, HA2 number(5,0), M65C char(1), HV015 number(2,0), M2E text, H12O text, M43 text, HV241 text, V751 number(2,0), SH218D number(2,0), M65I char(1), S104A number(2,0), HV237H char(1), HC18 number(3,0), V305 char(1), HML9 text, V463A text, V384B number(2,0), H46B char(1), HB50 text, HV232Y text, HV253F char(1), V623 number(2,0), V452A text, V833C char(1), V452C text, HB61 text, V770W text, B9 number(2,0), V506 text,
      HV214 number(3,0), HA4 number(5,0), V762BV text, V3A08M number(2,0), SH1D number(3,0), HB12 text, SH12 number(2,0), S325CF number(2,0), V479 char(1), V480 text, V3A00G text, HV111 text, S112D number(2,0), S114D number(2,0), SH110I number(2,0), H12W char(1), HML1A text, SH262 number(5,0), H32K number(2,0), S1209D number(2,0), V3A00T text, V821B char(1), V155 number(2,0), HV215 number(3,0), D115XC char(1), SH20G number(3,0), SH225 number(3,0), HB62 text, S506YD number(3,0), HC70 text,
      S112B number(2,0), S435GI number(2,0), H39 text, H40 char(1), SH281 number(5,0), V854B text, V413 text, SH130CD number(2,0), V372 text, HC72 text, V467C text, HV022 text, S1005 number(2,0), H4 text, V453 text, HC16 number(3,0), D115C number(2,0), G117F char(1), S536C number(3,0), VCOL number(2,0), D118U char(1), D119L number(2,0), HC56 number(4,0), D118F number(2,0), M55D text, D115Q number(2,0), D105G number(2,0), G100 number(2,0), M3L text, M61 text,
      ML13N char(1), V315 number(3,0), H37I text, H15A text, V770G text, V762AD text, V633F char(1), ML17B char(1), V239 text, V240 text, V3A08AA char(1), HA61 text, HW55 text, V508 number(5,0), M72 text, V841A char(1), HV108 number(3,0), H32O text, SHRM5 number(6,0), SH243 number(3,0), S326C number(2,0), S435GX number(2,0), HV035 number(2,0), D115XG char(1), S1204 number(2,0), S325FF number(2,0), HC6 text, HW16 number(3,0), SH13A number(2,0), SH13B number(2,0),
      V743E char(1), H32H text, S536B number(3,0), ML12 char(1), H35 char(1), H12F text, D110B number(2,0), M2L text, M3C text, M51 text, V472J char(1), V463C text, V473A text, H36B text, V414S text, V3A08C number(2,0), S325N number(2,0), S541F number(2,0), HA58 char(1), S523M number(2,0), ML17A text, SH19B number(3,0), SH219 number(2,0), HV021 text, HV211 number(2,0), SHCOMM number(3,0), S112G number(2,0), V105 char(1), HW7 text, V762BW char(1),
      HV028 text, V463D text, HML10 number(2,0), M11 text, S435GD number(2,0), V621 number(2,0), H12X text, SH08 number(2,0), M65J char(1), HV125 char(1), V469F text, V766B text, V206 number(2,0), M7 text, V539 char(1), V540 char(1), V770N number(2,0), S715ABD number(2,0), V762BX text, H15 text, M57O text, S305A number(3,0), H15K char(1), V3A00I text, V3A08K number(2,0), V3A09B char(1), D105B number(2,0), HV234 char(1), SH283M number(3,0), S541W number(2,0),
      V770T number(2,0), H37C char(1), D119Y number(2,0), G117E char(1), M35 char(1), ML21B char(1), V452B text, G102 number(2,0), SHRESI number(2,0), G117I char(1), V407 char(1), S113 number(2,0), V3A08W char(1), S715E number(2,0), V205 number(2,0), HB67 text, M57S text, HV024 number(2,0), D118J number(2,0), M34 text, V116 number(3,0), D119A char(1), HV005 text, V310 char(1), SH130CC number(2,0), V107 text, SH237 number(2,0), V744C number(2,0), SHRI number(5,0), M14 text,
      HC71 text, SHCONCES number(4,0), ML17C char(1), HC31 number(5,0), V770Q text, S536D char(1), H15D text, D118R number(2,0), V209 number(2,0), V210 number(2,0), D119I char(1), IDX94 number(2,0), V3A00Y number(2,0), V783 text, HC55 number(2,0), V241 text, H8 text, SH245 number(5,0), V505 text, H5 text, D101F number(2,0), S1309B2 number(2,0), H36D text, S523V number(2,0), V784R char(1), H32Z number(2,0), D102 number(2,0), H9Y text, S1401D number(2,0), V745B text,
      H36E char(1), SH104B number(3,0), S506I number(2,0), S435GJ number(2,0), V821A char(1), V151 number(2,0), SH284B number(4,0), V512 number(3,0), S506I2Y number(5,0), SH18 number(2,0), HV002 text, HA64 char(1), S1309A2 number(2,0), V3A00E number(2,0), M18 text, V125 text, V605 number(2,0), V3A08H number(2,0), D109 number(3,0), HB6 text, SH218C number(2,0), S523K number(2,0), M55A text, SH122A number(2,0), SH218H number(3,0), HV253H char(1), S1401C number(2,0), H12E text, ML18A text, V313 number(2,0),
      H12T text, V364 number(2,0), V472M char(1), H15E text, HV252 text, H12B text, V762AG char(1), D115P number(2,0), V482C char(1), V149 number(2,0), V150 number(3,0), V628 number(3,0), D113 number(2,0), V135 number(2,0), V127 number(3,0), V770B number(2,0), V401 text, D105J char(1), V854A text, M2C number(2,0), S1209B number(2,0), HV232C text, S1210 char(1), V784N text, S502X number(2,0), HB64 char(1), GIDX number(2,0), HV117 number(2,0), S523W number(2,0), G116 char(1),
      V414M text, HV114 text, B3 number(5,0)
    -> _All_
    -> AttributeExposer
AttributeExposer
    ATTR_LIST = fme_basename
    -> AttributeSplitter
AttributeSplitter
    DROP_EMPTY_PARTS = No
    LIST_NAME = _list
    ATTR_NAME = fme_basename
    TRIM_OPTION = Both
    DELIMITER = .
    -> ListIndexer
ListIndexer
    LIST_ATTR = _list{}
    PREFIX = _tbName
    INDEX = 1
    -> ListIndexer_2
ListIndexer_2
    LIST_ATTR = _list{}
    PREFIX = _filecode
    INDEX = 0
    -> AttributeRenamer
AttributeRenamer
    ATTR_LIST = _filecode_list,FileCode,
    -> Table1 (writer MDB_ADO_1)
Table1 (writer MDB_ADO_1)
    attributes: FileCode text(6)
_All_: Inspector [off]
schema (reader SCHEMA_FROM_TABLE_1)
    attributes: fme_feature_type_name varchar(200)
    -> schema
schema: Inspector
