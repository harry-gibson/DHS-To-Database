FME workspace Load_all_data_to_combined_db.fmw

Parameters:
- SourceDataset_CSV = \\129.67.26.176\map_data\DHS_Automation\DataExtraction\20150626_FullSiteScrape\ProcessedTables\222.HTIR52.*.csv   # Source CSV (CommaSeparatedValue) File(s)
- DestDataset_SQLITE3 = \\129.67.26.176\map_data\DHS_Automation\DataExtraction\20150626_FullSiteScrape\test_merger.sl3   # Destination SQLite Database File
- SourceDataset_SCHEMA_FROM_TABLE = $(FME_MF_DIR)AllSchemas_Flat.csv   # Source Dataset
- SourceDataset_PATH = \\129.67.26.176\map_data\DHS_Automation\DataExtraction\20150626_FullSiteScrape\ProcessedTables   # Source Folder and File Pathnames Folder
- DestDataset_POSTGRES = staging@map.zoo.ox.ac.uk:5434/dhs_data_pit   # Connection

Readers:
- CSV_1: CSV from $(SourceDataset_CSV)
- SCHEMA_FROM_TABLE_1: SCHEMA_FROM_TABLE from $(SourceDataset_SCHEMA_FROM_TABLE)
- PATH_1: PATH from $(SourceDataset_PATH)

Writers:
- SQLITE3_1: SQLITE3 to $(DestDataset_SQLITE3)
- POSTGRES_1: POSTGRES to $(DestDataset_POSTGRES)

CSV (reader CSV_1) [off]
    attributes: CASEID text, V201 number(3,0), V202 number(2,0), V203 number(2,0), V204 number(2,0), V205 number(2,0), V206 number(2,0), V207 number(2,0), V208 number(2,0), V209 number(2,0), V210 number(2,0), V211 number(5,0), V212 number(3,0), V213 number(2,0), V214 number(2,0), V215 number(4,0), V216 number(2,0), V217 number(2,0), V218 number(3,0), V219 number(3,0), V220 number(2,0), V221 number(4,0), V222 number(4,0), V223 number(2,0), V224 number(3,0), V225 number(2,0), V226 number(4,0), V227 number(2,0), V228 number(2,0), V229 number(3,0),
      V230 number(5,0), V231 number(5,0), V232 number(2,0), V233 number(2,0), V234 number(2,0), V235 number(2,0), V237 number(2,0), V238 number(2,0), V239 number(2,0), V240 number(3,0), V241 number(5,0), V242 number(5,0), V243 number(2,0), V784X number(2,0), S561A number(2,0), V763A number(2,0), ML13F number(2,0), V504 number(2,0), V851E number(2,0), V3A08R number(2,0), V003 number(3,0), V851A number(2,0), M65L char(1), D118T char(1), D119K number(2,0), D118XC char(1), V784L number(2,0), HV003 number(3,0), B7 number(4,0), ML22A char(1),
      V845 number(2,0), V704 number(4,0), M57M number(2,0), V767A number(2,0), MMC3 char(1), D103F char(1), V472E number(2,0), D105H number(2,0), HV208 number(2,0), V414J number(2,0), H11B number(2,0), V474G number(2,0), W117A number(2,0), SH28B number(3,0), V414Q number(2,0), V471C char(1), HW53 number(4,0), M42E number(2,0), W105C number(2,0), W131G char(1), HC60 number(4,0), V481A number(2,0), V326 number(3,0), V802 number(5,0), HV212 number(2,0), W148I char(1), HV001 number(3,0), H12I char(1), H32Q number(2,0), S518BL number(2,0),
      M42A number(2,0), H33Y number(5,0), W104B number(2,0), V161 number(3,0), S965A number(2,0), HD114 char(1), V509 number(5,0), V510 number(2,0), M57C char(1), V414B char(1), HB5 char(1), V032 number(2,0), HC13 number(2,0), H40M number(3,0), HC61 number(2,0), HW3 number(5,0), V768B number(4,0), H6 number(2,0), ML13Y number(2,0), MM1 number(2,0), HV246F number(3,0), HV105 number(3,0), HA52 number(2,0), V474J char(1), HB2 char(1), V743A number(2,0), V302 number(2,0), ML18C char(1), SH119A number(2,0), M2A number(2,0),
      M38 number(2,0), W125A char(1), V3A08O number(2,0), H32C char(1), ML19F char(1), HV031 number(4,0), W107A number(2,0), S148A number(2,0), V843 number(2,0), HV129 number(2,0), HV130 number(2,0), V461 char(1), H6Y number(5,0), V3A08P number(2,0), W112 number(2,0), SH119D number(2,0), HV243D number(2,0), V714 number(2,0), B1 number(3,0), V028 number(4,0), D118E char(1), HB13 char(1), HV121 number(2,0), M1C number(5,0), M8 number(3,0), ML14Z char(1), D115O number(2,0), S965G number(2,0), M55Z number(2,0), M57H char(1),
      M2I number(2,0), M47 number(2,0), V414A char(1), HC33 number(2,0), W131E char(1), M3G number(2,0), W103G char(1), W148X char(1), S152D number(2,0), SH32B number(3,0), HC7 number(5,0), MM3 number(3,0), M2M char(1), M3D char(1), D119XH number(2,0), HV247 number(2,0), V538 number(2,0), S518BF number(2,0), V467E number(2,0), M57D char(1), W107H char(1), V770P char(1), S536BB number(2,0), V472Q number(2,0), V778 number(2,0), V478 number(3,0), S536BF number(2,0), V754CP number(2,0), M42C number(2,0), HB41 char(1),
      V166 number(4,0), V744A number(2,0), V463B number(2,0), V770X number(2,0), V762AJ number(2,0), V762BA number(2,0), HV041 number(2,0), S561BB number(2,0), D103E char(1), HV204 number(4,0), V121 number(2,0), AWFACTW char(1), M6 number(3,0), V472S char(1), V474A number(2,0), SH145 number(2,0), HO101 number(2,0), ML16C number(2,0), H32D char(1), D120 char(1), HV115 number(2,0), D123 number(2,0), M19A number(2,0), D119XE number(2,0), V3A00L number(2,0), S518BX number(2,0), V537 number(3,0), HB12A char(1), D118XI char(1), SH112 number(3,0),
      S152I number(2,0), W122F number(2,0), HV243B number(2,0), D115H char(1), V784Q char(1), M49E char(1), D118XD char(1), M45 number(2,0), M2G number(2,0), HB1 number(3,0), D115R char(1), HV012 number(3,0), V104 number(3,0), HV017 number(2,0), HV235 number(2,0), V379 char(1), V380 char(1), S152C number(2,0), S965H number(2,0), V413A number(2,0), HV027 number(2,0), SH141 number(2,0), W103C char(1), V3A00Z number(2,0), V762AK number(2,0), V762BB number(2,0), H4M number(3,0), H5D number(3,0), HV019 number(3,0), HV020 number(2,0),
      H37K number(2,0), V851B number(2,0), V844 number(2,0), S1117 number(2,0), V770I char(1), HD108 char(1), D119XI char(1), W148E char(1), S1136A number(2,0), H0M number(3,0), D118XH char(1), ML13G char(1), D118W number(2,0), D119N char(1), SH144 number(2,0), M49X number(2,0), HV226 number(3,0), HA57 number(2,0), V784K number(2,0), W122B number(2,0), V474 number(2,0), H12H number(2,0), V412A number(2,0), M15 number(3,0), W103B char(1), S536BM number(2,0), ML13H number(2,0), ML15C char(1), V481C number(2,0), V614 number(2,0),
      V3A08Z number(2,0), W130K char(1), V008 number(5,0), W131B char(1), H37O number(2,0), S148X number(2,0), HC62 number(2,0), HB55 number(2,0), HB66 number(2,0), HA53 number(4,0), V119 number(2,0), V120 number(2,0), W107F number(2,0), V158 number(2,0), S518BM number(2,0), W118F char(1), V316 number(5,0), S965F number(2,0), M57U number(2,0), D103B number(2,0), HV014 number(2,0), H32L number(2,0), M3K number(2,0), M60 number(2,0), HW18 number(3,0), HC5 number(5,0), V375A char(1), V851K number(2,0), M65K char(1), ML19E char(1),
      D101C number(2,0), HV228 char(1), HA11 number(5,0), V633G char(1), S909H number(2,0), H2Y number(5,0), ML19Z char(1), V471D char(1), V465 number(3,0), S1121 number(2,0), V376 number(3,0), V471E char(1), V775 number(2,0), S536BX number(2,0), W121C number(2,0), S638Q number(2,0), D110H char(1), HV242 number(2,0), D110F char(1), V627 number(2,0), S636C number(2,0), W107X number(2,0), S151E number(2,0), HA12A number(6,0), D118H char(1), W129E number(2,0), W130E char(1), ML13C char(1), H7Y number(5,0), ML0 char(1),
      V770C number(2,0), V472A char(1), HD103 char(1), V762AI number(2,0), V762AR number(2,0), HV238 number(3,0), V307 number(2,0), V762BI number(2,0), D115XE number(2,0), V322 number(2,0), V743F number(2,0), W104A number(2,0), HB4 char(1), H12C char(1), W110 number(2,0), S518BO number(2,0), HA3 number(5,0), M65E number(2,0), M71 number(4,0), B12 number(4,0), D115XI char(1), H12D char(1), V019 char(1), V020 number(2,0), HV227 number(2,0), V770J number(2,0), S1108B number(2,0), ML2 char(1), V438 number(5,0), M57J char(1),
      V616 number(4,0), H37J number(2,0), D118A number(2,0), V820 number(2,0), H12U number(2,0), MM12 char(1), SH141A number(2,0), W129D number(2,0), W130D char(1), HO104 number(2,0), V414I number(2,0), V367 number(2,0), HV113 number(2,0), V761C number(2,0), V774C number(2,0), D105K char(1), W118G char(1), V762AX number(2,0), V762BO number(2,0), W125B char(1), D116 char(1), W127 number(2,0), S536BA number(2,0), V034 number(3,0), S965E number(2,0), W129C number(2,0), W130C char(1), HV237B number(2,0), S636A number(2,0), V3A00R number(2,0),
      V3A08S number(2,0), H32E char(1), V131 char(1), M49B number(2,0), ML13A char(1), H15I number(2,0), V603 number(4,0), V812 number(2,0), V321 number(2,0), HW58 char(1), HV237F number(2,0), SEDUC1 number(2,0), V304 number(2,0), M57P char(1), HV008 number(5,0), H3M number(3,0), ML13K number(2,0), ML14B char(1), H4D number(3,0), V604 number(2,0), D124 number(2,0), D119XJ char(1), S909M number(2,0), SVILLE number(4,0), V784I char(1), V129 number(3,0), V130 number(2,0), D118M char(1), V472T number(2,0), M55E number(2,0),
      V474B number(2,0), HV030 number(4,0), H38 number(2,0), D119D char(1), V471B number(2,0), V629 number(2,0), V838B number(2,0), MM10 char(1), V770R char(1), S518BN number(2,0), V3A08X number(2,0), V784V char(1), D119V char(1), V784A number(2,0), H31 number(2,0), V152 number(3,0), IDX95 number(2,0), V841 number(2,0), D115I char(1), S909Z number(2,0), H41B number(2,0), H15L char(1), HV246C number(3,0), H2D number(3,0), V414T number(2,0), H42 number(2,0), ML13J number(2,0), ML14A char(1), SEDUC number(2,0), HW6 number(6,0),
      MM7 number(3,0), W129J char(1), W130J char(1), B8 number(3,0), W131A char(1), H8M number(3,0), H9D number(3,0), H37F number(2,0), M1B number(3,0), M29 number(2,0), D119XD number(2,0), SH08A number(2,0), V3A08Q number(2,0), V827 number(2,0), V022 number(4,0), H9M number(3,0), HW12 number(6,0), W107D number(2,0), SH119C number(2,0), M4 number(3,0), V477 number(3,0), H15M char(1), V625 number(2,0), M13 number(2,0), V463F char(1), SHVILLE number(4,0), HB0 number(3,0), HV216 number(3,0), V103 char(1), S1001 number(2,0),
      V825 number(2,0), D101B number(2,0), V847 number(2,0), H32G number(2,0), V714A number(2,0), SH139 number(2,0), SH140 number(3,0), HV249 number(2,0), HV250 number(2,0), HV244 number(2,0), W125Y char(1), V472D char(1), ML21C char(1), V822 number(2,0), W121E number(2,0), H2M number(3,0), H3D number(3,0), M1 number(2,0), S518BG number(2,0), HV246I number(3,0), W103D char(1), HV102 number(2,0), H9 number(2,0), H15G number(2,0), V739 number(2,0), V740 number(2,0), HV009 number(3,0), HV010 number(2,0), IDXML number(2,0), W129G char(1),
      W130G char(1), ML13L number(2,0), M57I number(2,0), V762AS number(2,0), M49G char(1), V762BJ number(2,0), HV219 number(2,0), HV220 number(3,0), M55J char(1), D110E char(1), V3A05 number(2,0), D101G char(1), V823 number(2,0), V842 number(3,0), D110A number(2,0), V408 number(3,0), HV139 number(2,0), HV140 number(2,0), S518BI number(2,0), D115Y number(2,0), V784U char(1), M10 number(2,0), V838C number(2,0), V409 number(2,0), HV011 number(2,0), V410 number(2,0), D118XG char(1), HA67 number(2,0), V467K char(1), V743B number(2,0),
      HVIDX number(3,0), S536E number(2,0), HML1 number(3,0), V835B number(2,0), D115N char(1), D105F number(2,0), V824 number(2,0), HV251 number(2,0), V405 number(2,0), V395 number(2,0), V851C number(2,0), D121 number(2,0), V535 number(2,0), HB11 char(1), V850A number(2,0), D118I char(1), W104H char(1), W148C char(1), SH26 number(2,0), S536BG number(2,0), D119S char(1), D122A number(2,0), V829 number(3,0), H14 number(2,0), H12P number(2,0), V830 number(3,0), H32I char(1), AWFACTU number(4,0), HV237K char(1), SH147 number(3,0),
      V012 number(3,0), V633A number(2,0), S1116 number(2,0), S909J number(2,0), HV134 number(2,0), W104E number(2,0), HA50 number(2,0), V536 number(2,0), V762AN char(1), V762BE char(1), HV116 number(2,0), M55K char(1), V3A08B number(2,0), W131H char(1), MMC4 char(1), M65D number(2,0), HV236 number(2,0), H8Y number(5,0), H12J number(2,0), S152X number(2,0), B10 number(2,0), V472N number(2,0), D118P number(2,0), V527 number(4,0), D119G char(1), V784B number(2,0), D101J char(1), V784C number(2,0), HA35 number(2,0), H12Z number(2,0),
      S1125 number(2,0), D125 number(2,0), V472U number(2,0), V474C number(2,0), HC32 number(5,0), V376A number(2,0), W147 char(1), HV013 number(3,0), HV237E number(2,0), V414F number(2,0), H4Y number(5,0), HV209 number(2,0), HV210 number(2,0), HB58 char(1), ML13P number(2,0), D101H char(1), V472R number(2,0), BORD number(3,0), HD101 number(3,0), V631 char(1), D105C number(2,0), H37G char(1), ML15B char(1), S536BL number(2,0), MM14 number(2,0), V762BU number(2,0), H37A char(1), HV218 number(2,0), HV137 number(2,0), HC52 number(2,0),
      HB3 char(1), S151X number(2,0), V624 number(3,0), HV248 number(2,0), HV136 number(2,0), V762AC char(1), W101 number(2,0), MMC1 number(3,0), H5Y number(5,0), M27 number(2,0), M65X number(2,0), HC12 number(6,0), S909K number(2,0), V472G number(2,0), V415 number(2,0), S560 number(2,0), H43 number(2,0), V454 number(2,0), V719 number(2,0), B2 number(5,0), ML24C number(2,0), H3Y number(5,0), V761B number(2,0), S518BC number(2,0), HV118 number(2,0), H12G number(2,0), ML13Z number(2,0), S1004 number(2,0), H7 number(2,0), HW51 number(2,0),
      H32J number(2,0), V3A08L number(2,0), V613 number(3,0), ML19A char(1), ML20A char(1), V468 number(2,0), S561BD number(2,0), S636B number(2,0), V836 number(3,0), HB32 number(5,0), V3A01 number(2,0), HC11 number(5,0), M55C number(2,0), MM11 char(1), HA33 number(2,0), V027 number(2,0), HA6 number(6,0), V412B number(2,0), W103Y char(1), W105G char(1), S152J number(2,0), HA41 number(5,0), H2 number(2,0), V3A08G number(2,0), D107 number(2,0), V472H number(2,0), V784S number(2,0), S518BA number(2,0), V528 number(3,0), V325A number(8,0),
      HD102 char(1), MM8 number(5,0), V832C number(4,0), D110C char(1), V467M char(1), HO106 number(2,0), V732 number(2,0), SH132 number(3,0), B4 number(2,0), HB40 char(1), D118XK char(1), V763C number(2,0), V033 char(1), V767C number(3,0), V419 number(2,0), HV246J char(1), ML101 char(1), V420 char(1), HB63 number(2,0), S965B number(2,0), M69 number(3,0), M70 number(2,0), M36 number(3,0), D115K number(2,0), M42B char(1), V762AF char(1), V744D number(2,0), S151D number(2,0), B5 number(2,0), V467L char(1),
      V851F number(2,0), HW17 number(3,0), H20 number(2,0), V042 number(2,0), M3M char(1), M62 number(2,0), V157 number(2,0), V040 number(5,0), S965M number(2,0), S151A number(2,0), W123E number(2,0), HV000 char(4), V359 char(1), W121Y number(2,0), W123G char(1), H36A number(2,0), V360 char(1), HV246H number(2,0), V834C char(1), HC8 number(5,0), V762AP number(2,0), HA62 char(6), V762BG number(2,0), D105E number(2,0), V481F char(1), SH30A number(2,0), D127 number(3,0), H12S number(2,0), V851D number(2,0), V762AH number(2,0),
      S1137A number(2,0), W118C number(2,0), H12Y number(2,0), M55I number(2,0), V414P number(2,0), W123I char(1), M57N number(2,0), W122C number(2,0), M49Z number(2,0), HV138 number(2,0), V446 number(5,0), HV239 char(1), HV240 number(2,0), HB35 char(1), V3A00K number(2,0), V413D char(1), V784O number(2,0), M57L char(1), H6M number(3,0), V418 number(2,0), H7D number(3,0), HV213 number(3,0), W122D char(1), V311 number(2,0), V784F number(2,0), V472K number(2,0), V473B char(1), HA5 number(5,0), W129F number(2,0), W130F char(1),
      SH146 number(3,0), M55L char(1), ML23A char(1), V848 number(2,0), V122 number(2,0), D101E number(2,0), V044 number(2,0), HW52 number(2,0), W117B number(2,0), V414H number(2,0), ML13X number(2,0), M68 number(3,0), M2B number(2,0), M39 number(2,0), V805 number(4,0), SH128 number(2,0), W107C number(2,0), D119T char(1), D122B number(2,0), S518BH number(2,0), H15C number(2,0), V750 number(2,0), D118C number(2,0), V754JP number(2,0), HB51 number(2,0), H37M number(2,0), V849 number(2,0), V754BP number(2,0), M1D number(3,0), M57T number(2,0),
      V846 number(2,0), D118XJ char(1), M57A number(2,0), V770D number(2,0), V134 number(2,0), W145 char(1), D118Y number(2,0), D119P char(1), H32T number(2,0), V3A00F number(2,0), HA69 number(8,0), D119XG number(2,0), H41A char(1), S909I number(2,0), D119W char(1), V409A char(1), MMC5 number(3,0), V410A number(2,0), D115B number(2,0), S536BP number(2,0), V471F char(1), V437 number(5,0), HV023 number(2,0), ML19D char(1), HV101 number(3,0), H32F number(2,0), W128 number(2,0), D110D number(2,0), HV040 number(5,0), V463X number(2,0),
      V472C char(1), H37N number(2,0), M55X number(2,0), M57F number(2,0), V769 number(2,0), V770 number(2,0), V3A02 number(2,0), W122A number(2,0), V3A00H number(2,0), M2K number(2,0), M55M char(1), V141 number(2,0), M3B number(2,0), V323A number(3,0), W131D char(1), W131Y number(2,0), V414E number(2,0), W116 number(2,0), S1137D number(2,0), V462 char(1), W118H char(1), HA1 number(3,0), V837 char(1), V458 char(1), ML22B char(1), H37Z number(2,0), HV106 number(2,0), V701 number(2,0), W122J char(1), W123A number(2,0),
      V602 number(2,0), V439 number(5,0), V440 number(5,0), V633B number(2,0), HB53 number(4,0), V000 char(4), D103D char(1), V634 number(2,0), V014 number(2,0), V784D number(2,0), HV237 number(2,0), ML22C char(1), V312 number(3,0), HA56 number(4,0), ML13D number(2,0), D118L number(2,0), D119C char(1), W107G char(1), H36F char(1), MMIDX number(3,0), HML2 char(1), V774B number(2,0), SH119B number(2,0), H31C number(2,0), HD107 char(1), V502 number(2,0), D105A number(2,0), B11 number(4,0), V833B number(2,0), HC51 number(3,0),
      M55G number(2,0), ML13M number(2,0), H10 number(2,0), V803 number(3,0), M57R char(1), HC19 number(5,0), D115XJ char(1), ML16A char(1), V384A number(2,0), V756 number(2,0), M73 number(3,0), D115G number(2,0), M65H number(2,0), V413B number(2,0), HV109 number(2,0), HV110 char(1), V768C number(4,0), HW10 number(5,0), HD105 char(1), V754DP number(2,0), V3A00P number(2,0), V337 number(3,0), V784H char(1), S411E number(2,0), V761 number(2,0), V784J number(2,0), V762AE char(1), HV246 number(2,0), HV237X number(2,0), V411A number(2,0),
      HO103 number(2,0), V839 number(2,0), V840 number(2,0), M3H number(2,0), SHMETROP number(2,0), V457 number(2,0), V472O number(2,0), V762AV number(2,0), V762BM number(2,0), HV122 number(2,0), HV225 number(2,0), HV127 number(2,0), V005 number(8,0), M5 number(3,0), V007 number(5,0), V153 number(2,0), V472L number(2,0), HB52 number(2,0), MM5 char(1), S909D number(2,0), V814 number(2,0), H0D number(3,0), ML13E char(1), H22 number(2,0), W118D number(2,0), V159 number(2,0), V160 number(2,0), M2F number(2,0), M44 number(2,0), HV007 number(5,0),
      V043 number(2,0), V633E char(1), V762AO number(2,0), M57V char(1), V762BF char(1), V414C char(1), D118V number(2,0), D119M char(1), HA65 number(2,0), V102 number(2,0), V762BZ number(2,0), M64 number(3,0), H37L number(2,0), V762AQ number(2,0), V762BH number(2,0), V3A00N char(1), H32X number(2,0), S152F number(2,0), HC17 number(3,0), D118X number(2,0), D119O char(1), V124 number(2,0), HV207 number(2,0), V482B char(1), S926A number(2,0), HD104 char(1), HV044 number(2,0), H37D number(2,0), V467G number(2,0), W148G char(1),
      V414D char(1), V3A00J number(2,0), V731 number(2,0), V3A08N number(2,0), HW8 number(5,0), ML1 number(2,0), HB56 number(4,0), V024 number(3,0), BIDX number(3,0), HV033 char(1), W102 number(2,0), H12K number(2,0), H13B number(2,0), V762AW number(2,0), V762BN char(1), V763E char(1), V137 number(2,0), V138 number(2,0), HV246G number(3,0), S909A number(2,0), V128 number(3,0), W107E number(2,0), D119XA char(1), V476 number(2,0), REC84_GROUP char(1), HC58 char(1), D115S char(1), D117A number(2,0), HIDX number(2,0), HV103 number(2,0),
      HV221 number(2,0), HV246A char(1), M49A number(2,0), H12L number(2,0), HV237C number(2,0), HV246E number(3,0), V784T char(1), V744B number(2,0), V015 number(2,0), HC53 number(4,0), V006 number(3,0), V3A08A number(2,0), V447A number(3,0), V3A04 number(2,0), S532B number(2,0), S518D number(3,0), W103X char(1), W105F char(1), V414R char(1), S965L number(2,0), S536BJ number(2,0), V784E number(2,0), V3A08F number(2,0), H32A number(2,0), S1108A number(2,0), SH32A number(2,0), H32P number(2,0), V768A number(4,0), V481B number(2,0), S1007 number(2,0),
      V813 number(2,0), W148H char(1), M49C char(1), HB68 number(2,0), B13 number(2,0), W122H char(1), V541 number(2,0), V481D number(2,0), W148J char(1), HC3 number(5,0), HB60 number(2,0), V762AM number(2,0), V762BD char(1), V762AA number(2,0), W105B number(2,0), V832B number(4,0), V811 number(2,0), V406 number(2,0), D118Q number(2,0), V001 number(3,0), D119H number(2,0), D119X number(2,0), V474D number(2,0), W118B number(2,0), V466 char(1), V784P char(1), S152A number(2,0), H12R char(1), M3J number(2,0), W105H char(1),
      HV128 number(3,0), HW5 number(5,0), V414K number(2,0), V715 number(3,0), V770V char(1), MIDX number(2,0), V444A number(5,0), D103C number(2,0), SH135 number(3,0), W121D number(2,0), H31E number(2,0), S152G number(2,0), D115E char(1), W104G number(2,0), V3A00C char(1), ML19X char(1), D114 number(2,0), V529 number(4,0), V530 number(2,0), V511 number(3,0), V770L number(2,0), V413C char(1), M51A number(4,0), V503 number(2,0), H15H number(2,0), V3A00Q number(2,0), V763G char(1), S518BD number(2,0), D101D number(2,0), M57Q char(1),
      V774A number(2,0), V3A06 number(2,0), V481E number(2,0), H12V number(2,0), D115XF char(1), AWFACTT number(4,0), H32U number(2,0), V025 number(2,0), V834B number(3,0), M42D number(2,0), HC1 number(3,0), H3 number(2,0), V463G char(1), V3A00D char(1), D118S char(1), D119J number(2,0), HV206 number(2,0), D005 number(8,0), S518BQ number(2,0), D119XK char(1), H7M number(3,0), M17 number(2,0), M57X number(2,0), H8D number(3,0), V3A00S number(2,0), V741 number(2,0), MM15 char(1), V779 number(2,0), V780 number(2,0), D105D number(2,0),
      V464 number(3,0), S909C number(2,0), MMC2 number(3,0), REC31_GROUP number(5,0), V414N number(2,0), V3A03 number(2,0), ML13O number(2,0), V507 number(3,0), H15B number(2,0), D110G char(1), H31D number(2,0), D108 number(2,0), V3A00W char(1), HV245 number(3,0), V762AB number(2,0), S411F number(2,0), D101I char(1), W130H char(1), W129H char(1), HV237Z number(2,0), V838A number(2,0), S438 number(3,0), D115W number(2,0), H37E char(1), HA13 number(2,0), V482A char(1), H13 number(2,0), M55H number(2,0), V762AT number(2,0), V762BK number(2,0),
      H0 number(2,0), V474E number(2,0), HV026 number(2,0), M55B number(2,0), D115L number(2,0), W129I char(1), W130I char(1), V455 number(2,0), V481H char(1), S964 number(2,0), HV004 number(3,0), D118D number(2,0), V763F char(1), S965X number(2,0), W123C number(2,0), V190 number(2,0), D105I number(2,0), D118B number(2,0), W148F char(1), M55N char(1), V744E number(2,0), HA12 number(6,0), HB57 number(2,0), V3A00V number(2,0), H0Y number(5,0), V106 number(2,0), HV202 number(3,0), H45 char(1), V372A number(2,0), M2D char(1),
      SH30B number(3,0), HV132 number(2,0), V363 number(3,0), M2N number(2,0), M3E char(1), D118XB char(1), M49F char(1), HO105 number(2,0), HA54 number(2,0), HV107 number(3,0), V3A09A number(4,0), V3A08J number(2,0), HV246D number(3,0), ML11 number(2,0), V474H char(1), HW13 number(2,0), W118A number(2,0), HV018 number(4,0), V763D char(1), HD100 number(2,0), AWFACTE number(4,0), V632 number(2,0), V412 char(1), ML14Y char(1), W115 number(3,0), V467H number(2,0), V004 number(3,0), W122I char(1), S636D number(2,0), HV032 number(2,0),
      HV237I char(1), V472P number(2,0), HA55 number(2,0), S536BK number(2,0), V3A08V char(1), V3A00A number(2,0), D119XB number(2,0), V3A08D number(2,0), HA0 number(3,0), D115J number(2,0), HV016 number(3,0), ML16B char(1), HW56 number(5,0), H37H number(2,0), V414U number(2,0), SH134 number(2,0), S965C number(2,0), HC68 number(2,0), ML19C char(1), ML20C char(1), S965N number(2,0), H5M number(3,0), H6D number(3,0), M65G number(2,0), W104C number(2,0), H32Y number(2,0), S536BE number(2,0), S536BI number(2,0), V3A08E number(2,0), D115U char(1),
      ML19Y char(1), W105A number(2,0), V3A07 number(3,0), V472F number(2,0), AWFACTR number(4,0), HC10 number(5,0), V702 number(3,0), V417 number(2,0), V834A number(3,0), HV006 number(3,0), H44C number(2,0), D119Q char(1), V474F number(2,0), V851I number(2,0), V626 number(2,0), HA63 number(2,0), D105M char(1), S1124 number(3,0), HV243C number(2,0), D115T char(1), B16 number(3,0), M67 number(4,0), W121B number(2,0), H12M number(2,0), D115XD char(1), HV246B number(3,0), D118N char(1), HV270 number(2,0), D119E char(1), M57B number(2,0),
      W118I char(1), V362 number(2,0), M2H number(2,0), M46 number(4,0), SH23 number(2,0), S536BC number(2,0), V3A08T number(2,0), HB33 number(2,0), W107Y number(2,0), V319 number(2,0), V320 number(2,0), M3F number(2,0), M54 number(2,0), V301 number(2,0), M49D number(2,0), S1137C number(2,0), V705 number(3,0), V717 number(3,0), S965K number(2,0), HW2 number(4,0), V785 number(2,0), M9 number(3,0), V762BS number(2,0), HO102 number(2,0), V826 number(2,0), H34 number(2,0), V472I number(2,0), D115XA char(1), HW57 number(2,0), V770F number(2,0),
      M19 number(5,0), S909E number(2,0), S561BA number(2,0), D115XB char(1), V721 number(2,0), V421 char(1), V318 number(2,0), D119U number(2,0), D122C number(2,0), S518BJ number(2,0), MM6 number(3,0), V766A number(3,0), S536BD number(2,0), D104 number(2,0), HA32 number(5,0), ML15A char(1), V467A char(1), ML23B char(1), HA60 number(2,0), HV042 number(2,0), V828 number(2,0), MM2 number(2,0), HV124 number(3,0), V445 number(5,0), HV133 number(2,0), H36C number(2,0), HC27 number(2,0), HV237D number(2,0), S518BK number(2,0), V002 number(4,0),
      V113 number(3,0), D115XH char(1), W126 char(1), V123 number(2,0), V393 number(2,0), V136 number(3,0), S1002 number(2,0), V532 number(2,0), W131X char(1), V833A number(2,0), HHID text, MM4 number(5,0), SH24 number(2,0), S965D number(2,0), S152H number(2,0), V447 number(2,0), V475 number(2,0), D118XE number(2,0), SH25 number(2,0), HC15 number(2,0), ML13B number(2,0), W121G char(1), M1A number(2,0), HC0 number(3,0), M28 number(2,0), V115 number(4,0), D115M char(1), SH27 number(2,0), S152B number(2,0), H21A number(2,0),
      V139 number(3,0), V140 number(2,0), HO107 number(2,0), H32V number(2,0), H33M number(3,0), H40D number(3,0), V501 number(2,0), SLANG number(2,0), HV237A number(2,0), B15 number(2,0), HV043 number(2,0), M1E number(5,0), HA66 number(2,0), H32N char(1), V471G char(1), V443 number(6,0), HC2 number(5,0), W122E number(2,0), S518BY number(2,0), V801 number(5,0), S1108C number(2,0), HB65 number(2,0), V474I char(1), D119R char(1), W105D number(2,0), V411 number(2,0), ML21A char(1), V777 number(2,0), HV237G number(2,0), HV123 number(2,0),
      D128 number(2,0), H40Y number(5,0), H37Y number(2,0), W121A number(2,0), D119XF number(2,0), V467B number(2,0), V831 number(2,0), HV217 number(2,0), SH137 number(2,0), D112A number(2,0), HV025 number(2,0), W124 number(2,0), H32R char(1), V414G number(2,0), S561BX number(2,0), HWIDX number(2,0), V762BR number(2,0), W148A char(1), D101A number(2,0), V463Z number(2,0), W131C char(1), V101 number(3,0), V414L number(2,0), D115V number(2,0), H31B number(2,0), V404 number(2,0), V394 number(2,0), W104F number(2,0), HW15 number(2,0), V384C number(2,0),
      V531 number(3,0), V471A char(1), S518E number(3,0), W103E char(1), M57G char(1), HA40 number(5,0), V317 number(5,0), H44A number(3,0), V416 number(2,0), V456 number(4,0), HO100 number(3,0), W105E char(1), V023 number(2,0), M2J number(2,0), M3A number(2,0), M48 number(2,0), S1003 number(3,0), HW4 number(5,0), W123H char(1), HV126 number(2,0), V467D number(2,0), HV205 number(3,0), HA68 number(2,0), V444 number(6,0), HV246K char(1), V472B char(1), ML23C number(2,0), V835C number(2,0), V762AU number(2,0), V762BL number(2,0),
      HV120 number(2,0), V525 number(3,0), H32S number(2,0), B0 number(2,0), V016 number(3,0), V762BT number(2,0), V770K number(2,0), V3A00X number(2,0), S641Q number(2,0), V770U char(1), V767B number(2,0), V3A08I number(2,0), D115X number(2,0), W118E number(2,0), V743C number(2,0), S561BC number(2,0), V513 number(2,0), V442 number(6,0), HW11 number(5,0), S909L number(2,0), V804 number(2,0), HV131 number(2,0), D115D number(2,0), H37P number(2,0), V441 number(6,0), V3A00B number(2,0), HB69 number(8,0), D115F number(2,0), HV237J char(1), H32M number(2,0),
      H33D number(3,0), M65F number(2,0), S536BY number(2,0), MM9 number(2,0), HC30 number(3,0), D118O number(2,0), D119F char(1), D112 number(2,0), HB12B char(1), V762AZ number(2,0), V762BQ number(2,0), V770M number(2,0), V481X number(2,0), H15F number(2,0), D118XA char(1), V784M number(2,0), HA12B number(6,0), V835A number(2,0), HW1 number(3,0), V3A00U number(2,0), M57E number(2,0), M57K char(1), B6 number(4,0), S914 number(2,0), S518BP number(2,0), M55F number(2,0), HC9 number(6,0), H12A number(2,0), V754WP number(2,0), M66 number(2,0),
      ML13I number(2,0), V806 number(3,0), W123D char(1), V011 number(5,0), HD111 char(1), V770E number(2,0), W123F number(2,0), V3A00O number(2,0), V851J number(2,0), V821C char(1), V168 number(2,0), V133 number(3,0), V191 number(8,0), V3A08U char(1), H46A number(3,0), V414O number(2,0), S151B number(2,0), H11 number(2,0), V304A number(2,0), V762AL number(2,0), V762BC char(1), W107J char(1), HV112 number(2,0), H12N char(1), V729 number(2,0), V026 number(2,0), V730 number(3,0), V467F number(2,0), D119XC char(1), HC64 number(3,0),
      V474Z number(2,0), H32W number(2,0), HD106 char(1), V018 char(1), V426 number(4,0), V327 number(2,0), V784G char(1), D118K number(2,0), D119B char(1), V361 char(1), D118G number(2,0), HV271 number(8,0), W104D number(2,0), V481G char(1), D115XK char(1), HC57 number(2,0), V467J char(1), V770H char(1), HC4 number(5,0), V467I number(2,0), V459 number(2,0), V460 char(1), SH138 number(3,0), HD112 char(1), H33 number(2,0), HW19 number(5,0), H15J char(1), HDPIDX number(2,0), S636E number(2,0), V481 number(2,0),
      H12Q number(2,0), V633C char(1), V850B number(2,0), D126 number(3,0), V762BP number(2,0), V633D number(2,0), V3A00M char(1), HA51 number(2,0), M3N number(2,0), M3I number(2,0), W122G char(1), SH121F number(2,0), M63 number(4,0), HV243A number(2,0), H37B number(2,0), HD109 char(1), HD110 char(1), V769A number(2,0), V770A number(2,0), V156 number(2,0), W131F char(1), HC63 number(4,0), D103A number(2,0), MM13 char(1), S148C number(2,0), V763B number(2,0), M65B number(2,0), V716 number(4,0), D118XF char(1), V017 char(1),
      ML18B char(1), D105N char(1), V167 number(3,0), D111 number(2,0), V743D number(2,0), V770O number(2,0), H1 number(2,0), H21 number(2,0), V029 number(3,0), V030 number(4,0), V746 number(2,0), V770S number(2,0), W129B number(2,0), W130B char(1), W114 char(1), V463E char(1), W123J char(1), W107I char(1), IDXH4 number(3,0), H44B number(3,0), HV201 number(3,0), H32B number(2,0), W123B number(2,0), V323 number(3,0), D106 number(2,0), M65A number(2,0), HV104 number(2,0), ML19B char(1), V009 number(3,0), V010 number(5,0),
      V474X number(2,0), ML20B char(1), V851L number(2,0), W120 number(2,0), HD113 char(1), HW9 number(6,0), V851H number(2,0), D105L char(1), V851G number(2,0), H37X number(2,0), V781 number(2,0), HA2 number(5,0), M65C number(2,0), V013 number(2,0), HV015 number(2,0), S909B number(2,0), M2E char(1), M43 number(2,0), H12O number(2,0), HV241 number(2,0), V751 number(2,0), M65I char(1), HC18 number(3,0), HV237H number(2,0), V305 number(2,0), S151C number(2,0), V463A number(2,0), HB50 number(2,0), H46B number(2,0), S965I number(2,0),
      V384B number(2,0), V623 number(2,0), V452A number(2,0), V833C char(1), V452C number(2,0), HB61 number(2,0), V770W char(1), B9 number(2,0), V506 number(2,0), HV214 number(3,0), HA4 number(5,0), V762BV number(2,0), V3A08M number(2,0), S965J number(2,0), HB12 char(1), S536BQ number(2,0), V479 number(3,0), V480 number(2,0), V031 number(4,0), HV111 number(2,0), V3A00G number(2,0), H12W number(2,0), HML1A char(1), H32K number(2,0), V3A00T number(2,0), W148D char(1), SH136 number(2,0), V821B number(2,0), V155 number(2,0), HV215 number(3,0),
      SMETROP number(2,0), D115XC char(1), W146 char(1), W100 number(2,0), HB62 char(6), H39 number(2,0), H40 number(2,0), S909N number(2,0), V413 number(2,0), V372 number(2,0), V467C number(2,0), HV022 number(4,0), S1005 number(2,0), H4 number(2,0), V453 number(4,0), HC16 number(3,0), D115C number(2,0), D118U char(1), D119L char(1), HC56 number(4,0), D118F number(2,0), M55D number(2,0), D115Q number(2,0), D105G char(1), W121F number(2,0), M3L char(1), M61 number(4,0), ML13N number(2,0), V315 number(3,0), H37I number(2,0),
      H15A number(2,0), V770G char(1), V762AD char(1), ML17B char(1), V633F char(1), HA61 number(2,0), W107B number(2,0), HW55 number(2,0), W103A char(1), V508 number(5,0), M72 number(3,0), HV108 number(3,0), H32O number(2,0), HV035 number(2,0), D115XG char(1), HC6 number(6,0), SH149 number(4,0), SH150 number(2,0), HW16 number(3,0), V743E char(1), H32H number(2,0), ML12 char(1), H35 number(2,0), H12F number(2,0), D110B number(2,0), M2L char(1), M3C number(2,0), V414S number(2,0), HA58 char(1), V463C number(2,0),
      V472J number(2,0), V473A char(1), ML17A char(1), H36B number(2,0), S909G number(2,0), V3A08C number(2,0), HV021 number(3,0), HV211 number(2,0), S1137B number(2,0), V105 number(2,0), HW7 number(5,0), HV028 number(8,0), W132 char(1), S536BO number(2,0), V463D number(2,0), V762BW number(2,0), M11 number(4,0), S1118A number(2,0), V621 number(2,0), H12X number(2,0), M65J char(1), HV125 number(2,0), V766B number(3,0), M7 number(3,0), V539 number(2,0), V540 number(2,0), S601W number(2,0), V770N number(2,0), V762BX number(2,0), M57O number(2,0),
      H15 number(2,0), W148B char(1), H15K char(1), V3A00I char(1), V3A08K number(2,0), V3A09B number(4,0), D105B number(2,0), HV234 number(4,0), HV135 number(2,0), V770T number(2,0), H37C char(1), D119Y number(2,0), S1006 number(2,0), M35 number(3,0), S518BB number(2,0), ML21B char(1), V452B number(2,0), V407 number(3,0), V3A08W char(1), S518BE number(2,0), HB67 number(3,0), W129A number(2,0), W130A char(1), M57S number(2,0), HV024 number(3,0), S148B number(2,0), M34 number(4,0), V116 number(3,0), D118J number(2,0), HV005 number(8,0),
      D119A char(1), V310 number(3,0), HOVIDX number(3,0), V107 number(3,0), V744C number(2,0), M14 number(3,0), ML17C char(1), HC31 number(5,0), V770Q char(1), S536D number(3,0), V021 number(3,0), H15D number(2,0), D118R char(1), D119I number(2,0), IDX94 number(2,0), V3A00Y number(2,0), HC55 number(2,0), V783 number(2,0), H8 number(2,0), V505 number(3,0), H5 number(2,0), D101F number(2,0), H36D char(1), V784R char(1), H32Z number(2,0), S1108D number(2,0), D102 number(2,0), H9Y number(5,0), H36E char(1), V019A char(1),
      S536BN number(2,0), V821A number(2,0), V151 number(2,0), V512 number(3,0), HA64 char(1), HV002 number(4,0), S909F number(2,0), V3A00E char(1), M18 number(2,0), V125 number(2,0), W103F char(1), V3A08H number(2,0), V605 number(2,0), HB6 char(1), S909X number(2,0), S1119A number(2,0), D109 number(3,0), M55A number(2,0), S443 number(3,0), ML18A char(1), H12E char(1), V313 number(2,0), HO108 number(2,0), H12T number(2,0), V364 number(2,0), V472M number(2,0), H15E number(2,0), H12B number(2,0), V762AG number(2,0), D115P number(2,0),
      V482C char(1), V149 number(2,0), V150 number(3,0), V628 number(2,0), SH28A number(2,0), D113 number(2,0), V135 number(2,0), V127 number(3,0), V401 number(2,0), V770B number(2,0), S152E number(2,0), D105J number(2,0), M2C number(2,0), V784N number(2,0), HB64 char(1), S536BH number(2,0), HV117 number(2,0), HV114 number(3,0), V414M number(2,0), B3 number(5,0)
    -> AttributeExposer
AttributeExposer [off]
    ATTR_LIST = fme_basename
    -> StringSearcher
StringSearcher [off]
    MATCHED_PARTS_ATTR = _
    STRING_TO_SEARCH = @Value(fme_basename)
    MATCHED_RESULT_ATTR = _matched_characters
    REGEXP = ^(\d+)\.(\w+)\.(.+)$
    CASE = no
PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> StringSearcher_2
StringSearcher_2
    MATCHED_PARTS_ATTR = _
    STRING_TO_SEARCH = @Value(path_rootname)
    MATCHED_RESULT_ATTR = _matched_characters
    REGEXP = ^(\d+)\.(\w+)\.(.+)$
    CASE = no
    MATCHED -> ListIndexer
ListIndexer
    PREFIX = SurveyID
    LIST_ATTR = _{}
    INDEX = 0
    -> ListIndexer_2
ListIndexer_2
    PREFIX = RecordName
    LIST_ATTR = _{}
    INDEX = 2
    -> AttributeRenamer
AttributeRenamer
    ATTR_LIST = RecordName_,tablename,,SurveyID_,SurveyID,
    -> Tester
Note: Don't load data from the country-specific tables as these have vast numbers of columns due to their being different in each survey. / (e.g. REC91 would have 14007 columns!!) / If we want to do anything with those data we'd have to restructure for storage in a single attr name / value table?
Tester
    TEST_CLAUSE:
      TEST @Value(tablename) NOT_IN REC91,REC95,RECH3,REC94,REC97,REC98,RECH4,RECH8,REC99,RECH7,RECHG2
      TEST @Value(SurveyID) = 222
    TEST_DESCRIPTION = ""
    TEST_MODE = Automatic
    BOOL_OP = AND
    PASSED -> FeatureReader
FeatureReader
    CSV__IN_FIELD_NAMES = YES
    CSV__IN_SEPARATOR = ,
    CSV__SCHEMA = char,12,,char,6,,char,17,
    CSV__SKIP_LINES = 1
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    ATTR_CONFLICT_RES = Use Result
    CSV_SCAN_MAX_FEATURES = 1000
    ATTR_ACCUM_MODE = Merge Initiator and Result
    CSV__STRIP_QUOTES = yes
    CSV__GROUP_BY_DATASET = no
    FORMAT = CSV
    CSV__FIELD_NAMES_AFTER_HEADER = no
    DATASET = @Value(path_windows)
    CSV__ALLOW_SPACES_IN_COLUMN_NAMES = yes
    COMBINE_GEOM = Use Result
    CSV__SKIP_FOOTER = 0
    FEATURETYPES_RADIO = FEATURETYPES
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    CSV__SCHEMA_WITH_COL_NAMES = name,char,12,,RecordName,char,6,,coltype,char,17,
    CSV__DUPLICATE_DELIMS = no
    OUTPUT_FEATURES_DISPLAY = Based on Connections
    <OTHER> -> dhs_data_tables.Table1 (writer POSTGRES_1)
dhs_data_tables.Table1 (writer POSTGRES_1)
Table1 (writer SQLITE3_1)
