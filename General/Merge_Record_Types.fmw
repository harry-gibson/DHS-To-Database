FME workspace Merge_Record_Types.fmw

Parameters:
- SourceDataset_CSV = \\129.67.26.176\map_data\DHS_Automation\DataExtraction\20150626_FullSiteScrape\ParsedSpecs\*.FlatRecordSpec.csv   # Source CSV (CommaSeparatedValue) File(s)
- FEATURE_TYPES =
- DestDataset_CSV = \\129.67.26.176\map_data\DHS_Automation\DataExtraction\20150626_FullSiteScrape\ParsedSpecs_ByRecordType   # Destination CSV (CommaSeparatedValue) Folder

Readers:
- CSV_1: CSV from $(SourceDataset_CSV)

Writers:
- CSV_2: CSV to $(DestDataset_CSV)

CSV (reader CSV_1)
    attributes: FileCode text, RecordName text, RecordTypeValue text, RecordLabel text, Name text, Label text, Start text, Len text, Occurrences text, ZeroFill text, DecimalChar text, Decimal text, FMETYPE text
    -> AttributeExposer
AttributeExposer
    ATTR_LIST = fme_basename
    -> StringSearcher
StringSearcher
    REGEXP = ^\d+
    CASE = no
    STRING_TO_SEARCH = @Value(fme_basename)
    MATCHED_RESULT_ATTR = SurveyID
    MATCHED_PARTS_ATTR = _matched_parts
    MATCHED -> AttributeRemover
AttributeRemover
    LIST_ATTRS = _matched_parts{}
    -> AllSpecsAllSurveys (writer CSV_2)
AllSpecsAllSurveys (writer CSV_2)
    attributes: SurveyID text, FileCode text, RecordName text, RecordTypeValue text, RecordLabel text, Name text, Label text, Start text, Len text, Occurrences text, ZeroFill text, DecimalChar text, Decimal text, FMETYPE text
