FME workspace CheckMissingRegionalBoundaries.fmw

Parameters:
- SourceDataset_SHAPE = C:\Users\zool1301\Documents\DHS\DHS_Info\dhs_subnational_boundaries_all_avail_surveys.shp   # Source Esri Shape File(s)
- SourceDataset_PATH = \\129.67.26.176\map_data\DHS_Automation\DataExtraction\20150626_FullSiteScrape\ProcessedTables   # Source Folder and File Pathnames Folder

Readers:
- SHAPE_1: SHAPE from $(SourceDataset_SHAPE)
- PATH_1: PATH from $(SourceDataset_PATH)

Note: Builds a list of survey IDs for which we do not have regional polygon data. This can be used to see if the data now exist (hint: they probably still don't) on the DHS SDR website, either manually or via the geoprocessing service at http://gis101.measuredhs.com/arcgis/rest/services/SDR/DownloadSubnationalData/GPServer/downloadSubNationalBoundaries/submitJob
dhs_subnational_boundaries_all_avail_surveys (reader SHAPE_1)
    attributes: OBJECTID number(10,0), ISO char(2), FIPS char(2), DHSCC char(2), SVYTYPE char(3), SVYYEAR number(19,11), CNTRYNAMEE char(254), CNTRYNAMEF char(254), CNTRYNAMES char(254), DHSREGEN char(254), DHSREGFR char(254), DHSREGSP char(254), SVYID number(19,11), REG_ID char(15), Svy_Map char(3), MULTLEVEL char(3), LEVELRNK number(19,11), REGVAR char(254), REGCODE number(19,11), REGNAME char(254), OTHREGVAR char(254), OTHREGCO number(19,11), OTHREGNA char(254), LEVELCO char(254), LEVELNA char(254), REPALLIND char(254), REGNOTES char(254), SVYNOTES char(254), Shape_Leng number(19,11), Shape_Area number(19,11)
    -> AttributeKeeper_2
AttributeKeeper_2
    KEEP_ATTRS = SVYID
    -> Sampler
Sampler
    GROUP_BY = SVYID
    SAMPLE_TYPE_LONG = First N Features
    RATE = 1
    SAMPLED -> FeatureMerger [input 2]
    SAMPLED -> Sampler_Sampled
Sampler_Sampled: Inspector
PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> AttributeKeeper
AttributeKeeper
    KEEP_ATTRS = path_filename
    -> StringSearcher
StringSearcher
    STRING_TO_SEARCH = @Value(path_filename)
    MATCHED_PARTS_ATTR = _matched_parts
    MATCHED_RESULT_ATTR = _svyID
    CASE = no
    REGEXP = ^\d+
    MATCHED -> StringSearcher_Matched
    MATCHED -> FeatureMerger [input 1]
FeatureMerger
    ATTR_CONFLICT_RES = Use Requestor
    PROCESS_DUPS = No
    SUPPLIERS_FIRST = No
    JOIN_KEYS = @Value(_svyID) @Value(SVYID) AUTO
    ATTR_ACCUM_MODE = Merge Supplier
    MERGE_TYPE = Attributes Only
    IGNORE_NULLS = No
    NOT_MERGED -> ThatKidsGotNoBoundaries
    NOT_MERGED -> ListBuilder
ThatKidsGotNoBoundaries: Inspector
ListBuilder
    LIST_NAME = _list
    -> ListConcatenator
ListConcatenator
    DROP_EMPTY_PARTS = No
    SEP = ,
    VAL_ATTR = requireBoundaryIDs
    LIST_ATTR = _list{}._svyID
    -> ListConcatenator_Output
ListConcatenator_Output: Inspector
StringSearcher_Matched: Inspector
