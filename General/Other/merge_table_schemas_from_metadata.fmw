FME workspace merge_table_schemas_from_metadata.fmw

Parameters:
- SourceDataset_CSV = \\map-fs1.ndph.ox.ac.uk\map_data\DHS_Automation\DataExtraction\All\ParsedSpecs_Concat\SchemaMapperTableSpecs_AllTables_AllSurveys.csv   # Source CSV (Comma Separated Value) File(s)
- DestDataset_FFS = \\map-fs1.ndph.ox.ac.uk\map_data\DHS_Automation\DataExtraction\All\PG_Database_Load\All_Combined_Table_Schemas_FromMetadata.ffs   # Destination FME Feature Store (FFS) File

Readers:
- CSV_1: CSV from $(SourceDataset_CSV)

Writers:
- FFS_1: FFS to $(DestDataset_FFS)

CSV (reader CSV_1)
    attributes: ItemType char(17), SurveyIDDataColumnName char(9), SurveyID number(4,0), FileCode char(11), RecordName char(7), RecordTypeValue char(4), RecordLabel char(45), NameColumnName char(5), Name char(12), Label char(97), Start number(4,0), Len number(3,0), Occurrences number(3,0), ZeroFill char(4), DecimalChar char(3), Decimal char(1), FMETYPE char(13)
    -> StatisticsCalculator
StatisticsCalculator
    STATS_ATTRS = Len Start
    PREPEND_ATTR_NAME_CHOICE = For multiple results only
    COMPUTE_HISTOGRAM = NO
    MIN_ATTR = Min
    GROUP_BY = Name RecordName
    MAX_ATTR = Max
    SUMMARY -> AttributeManager
AttributeManager
    ATTR_TABLE:
      RENAME_SET_VALUE Name > name
      SET_TO fme_data_type = fme_varchar(@Value(Len.Max))
      REMOVE Len.Min
      REMOVE Len.Max
      RENAME_SET_VALUE Start.Min > StartMin
      REMOVE Start.Max
    -> ListBuilder
    -> DuplicateFilter
DuplicateFilter
    KEYATTR = RecordName
    INPUT_ORDERED_CHOICE = No
    UNIQUE -> AttributeKeeper
AttributeKeeper
    KEEP_ATTRS = RecordName
    -> AttributeCreator
AttributeCreator
    ATTR_TABLE:
      SET_TO name = SurveyID
      SET_TO fme_data_type = fme_varchar(3)
      SET_TO StartMin = -1
    -> ListBuilder
ListBuilder
    LIST_NAME = attribute
    GRP_BY = RecordName
    -> ListSorter
ListSorter
    ORDER = Ascending
    TYPE = Numeric
    SRC_LIST = attribute{}.StartMin
    -> AttributeRemover
AttributeRemover
    LIST_ATTRS = attribute{}.RecordName
    -> AllSchemas (writer FFS_1)
    -> AttributeRemover_Output
    -> ListElementCounter
AttributeRemover_Output: Inspector
AllSchemas (writer FFS_1)
    attributes: RecordName varchar(7), attribute{}.name varchar(200), attribute{}.fme_data_type varchar(200), attribute{}.StartMin varchar(200)
ListElementCounter
    LIST_NAME = attribute{}
    CNT_ATTR = _element_count
    -> ListElementCounter_Output
ListElementCounter_Output: Inspector
