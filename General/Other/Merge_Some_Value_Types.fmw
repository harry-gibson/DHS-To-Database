FME workspace Merge_Some_Value_Types.fmw

Parameters:
- SourceDataset_CSV =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   # Source CSV (CommaSeparatedValue) File(s)
- FEATURE_TYPES =
- DestDataset_CSV = \\129.67.26.176\map_data\DHS_Automation\DataExtraction\20150626_FullSiteScrape\ParsedSpecs_ByRecordType   # Destination CSV (CommaSeparatedValue) Folder

Readers:
- CSV_1: CSV from $(SourceDataset_CSV)

Writers:
- CSV_2: CSV to $(DestDataset_CSV)

CSV (reader CSV_1)
    attributes: FileCode text, Name text, Value text, ValueDesc text, ValueType char(14)
    -> AttributeExposer
StringSearcher_2
    MATCHED_RESULT_ATTR = _matched_characters
    STRING_TO_SEARCH = @Value(Name)
    REGEXP = HC[0-9]|HML|HV1
    CASE = no
    MATCHED_PARTS_ATTR = _matched_parts
    MATCHED -> AttributeExposer
AttributeExposer
    ATTR_LIST = fme_basename
    -> StringSearcher
StringSearcher
    MATCHED_RESULT_ATTR = SurveyID
    STRING_TO_SEARCH = @Value(fme_basename)
    REGEXP = ^\d+
    CASE = no
    MATCHED_PARTS_ATTR = _matched_parts
    MATCHED -> AttributeRemover
AttributeRemover
    LIST_ATTRS = _matched_parts{}
    -> All_ValueSpecs_NearlyAllSurveys (writer CSV_2)
All_ValueSpecs_NearlyAllSurveys (writer CSV_2)
    attributes: SurveyID char(14), FileCode text, Name text, Value text, ValueDesc text, ValueType char(14)
