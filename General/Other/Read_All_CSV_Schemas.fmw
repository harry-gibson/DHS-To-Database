FME workspace Read_All_CSV_Schemas.fmw

Parameters:
- SourceDataset_SCHEMA = \\map-fs1.ndph.ox.ac.uk\map_data\DHS_Automation\DataExtraction\All\ProcessedTables\*.csv   # Source Dataset
- SCHEMA_IN_REAL_FORMAT_SCHEMA = GUESS_FROM_EXTENSION   # Input Format
- FEATURE_TYPES =
- DestDataset_FFS = \\map-fs1.ndph.ox.ac.uk\map_data\DHS_Automation\DataExtraction\All\PG_Database_Load\All_CSV_Schemas.ffs   # Destination FME Feature Store (FFS) File

Readers:
- SCHEMA_1: SCHEMA from $(SourceDataset_SCHEMA)

Writers:
- FFS_1: FFS to $(DestDataset_FFS)

Note: Here we just read all the schemas of ALL the csv files and dump them out to an FFS file (this is the only format supporting a list attribute)
schema (reader SCHEMA_1)
    attributes: fme_feature_type_name varchar(200)
    -> _All_
    -> schema (writer FFS_1)
schema (writer FFS_1)
    attributes: fme_feature_type_name varchar(200), attribute{}.name varchar(200), attribute{}.fme_data_type varchar(200), attribute{}.native_data_type varchar(200), fme_format_long_name varchar(200), fme_format_short_name varchar(200)
_All_: Inspector
