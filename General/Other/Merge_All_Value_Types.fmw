FME workspace Merge_All_Value_Types.fmw

Parameters:
- SourceDataset_CSV = \\129.67.26.176\map_data\DHS_Automation\DataExtraction\All\ParsedSpecs_NoExpansion\*.FlatValuesSpec.csv   # Source CSV (CommaSeparatedValue) File(s)
- FEATURE_TYPES =
- DestDataset_CSV = \\129.67.26.176\map_data\DHS_Automation\DataExtraction\All\ParsedSpecs_Concat_NoExpansion   # Destination CSV (CommaSeparatedValue) Folder

Readers:
- CSV_1: CSV from $(SourceDataset_CSV)

Writers:
- CSV_2: CSV to $(DestDataset_CSV)

CSV (reader CSV_1)
    attributes: FileCode text, Name text, Value text, ValueDesc text, ValueType char(14)
    -> AttributeExposer
StringSearcher_2
    MATCHED_PARTS_ATTR = _matched_parts
    CASE = no
    REGEXP = HC[0-9]|HML|HV1
    STRING_TO_SEARCH = @Value(Name)
    MATCHED_RESULT_ATTR = _matched_characters
    MATCHED -> AttributeExposer
AttributeExposer
    ATTR_LIST = fme_basename
    -> StringSearcher
StringSearcher
    MATCHED_PARTS_ATTR = _matched_parts
    CASE = no
    REGEXP = ^\d+
    STRING_TO_SEARCH = @Value(fme_basename)
    MATCHED_RESULT_ATTR = SurveyID
    MATCHED -> AttributeRemover
AttributeRemover
    LIST_ATTRS = _matched_parts{}
    -> All_ValueSpecs_AllSurveys (writer CSV_2)
All_ValueSpecs_AllSurveys (writer CSV_2)
    attributes: SurveyID char(14), FileCode text, Name text, Value text, ValueDesc text, ValueType char(14)
