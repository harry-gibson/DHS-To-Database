FME workspace Load_DHS_Data_To_PG_With_Checks.fmw

Parameters:
- SourceDataset_FFS = \\map-fs1.ndph.ox.ac.uk\map_data\DHS_Automation\Acquisition\All_MR\pg_database_load\MR_Initial_Combined_Table_Schemas_FromMetadata.ffs   # Source FME Feature Store (FFS) File(s)
- SourceDataset_PATH = \\map-fs1.ndph.ox.ac.uk\map_data\DHS_Automation\Acquisition\All_MR\tables   # Source Folder and File Pathnames Folder
- DestDataset_POSTGRES = Admin on MAP-FS1   # Connection
- DestDataset_CSV = \\map-fs1.ndph.ox.ac.uk\map_data\DHS_Automation\Acquisition\All_MR   # Destination CSV (Comma Separated Value) Folder

Readers:
- FFS_1: FFS from $(SourceDataset_FFS)
- PATH_1: PATH from $(SourceDataset_PATH)

Writers:
- POSTGRES_1: POSTGRES to $(DestDataset_POSTGRES)
- CSV_1: CSV to $(DestDataset_CSV)

Note: Read the names of all the survey CSV tables
PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> StringSearcher_3
StringSearcher_3
    REGEXP = ^\d+
    STRING_TO_SEARCH = @Value(path_filename)
    MATCHED_RESULT_ATTR = SurveyID_File
    CASE = no
    MATCHED -> StringSearcher_2
StringSearcher_2
    REGEXP = M?REC[0-9A-Z]{2,4}
    STRING_TO_SEARCH = @Value(path_filename)
    MATCHED_RESULT_ATTR = RecordName_File
    CASE = no
    MATCHED -> Matcher
    NOT_MATCHED -> Duplicate_Tbl_File_Skipped
Note: Is it that stupid survey 156 with lots of copies of each table?
Matcher
    LENIENT_MATCH = No
    MATCH_STRATEGY = Match Selected Attributes
    BLANK_AND_MISSING_DIFFER = No
    MATCHATTRS = RecordName_File SurveyID_File
    CNT_ATTR = _match_id
    MATCH = 2D
    MATCHED -> Duplicate_Tbl_File_Skipped
    NOT_MATCHED -> FeatureMerger [REQUESTOR]
    NOT_MATCHED -> Files_To_Check
Duplicate_Tbl_File_Skipped: Inspector
Files_To_Check: Inspector
Note: Get the names of tables that have alrady been created
SQLCreator
    DATASET = DHS Data Readonly
    POSTGRES_NAMED_CONNECTION = DHS Data Readonly
    POSTGRES_QUERY_FEATURE_TYPES_FOR_MERGE_FILTERS = Yes
    EXPOSED_ATTRIBUTE_LIST = table_name
    POSTGRES_SCHEMAS_FOR_TABLE_LISTING = dhs_data_tables
    FORMAT = POSTGRES
    SQL_STATEMENT:
      SELECT table_name
      FROM information_schema.tables
      WHERE table_name LIKE '%REC%'
    RESULT -> SQLExecutor_2 [INITIATOR]
    RESULT -> FeatureMerger [SUPPLIER]
    <REJECTED> -> Terminator
Terminator
    MESSAGE = Translation Terminated
Note: Get the number of rows already existing for each survey in the DB table
SQLExecutor_2
    DATASET = DHS Data Readonly
    POSTGRES_NAMED_CONNECTION = DHS Data Readonly
    COMBINE_GEOM = Initiator Geometry Only
    POSTGRES_QUERY_FEATURE_TYPES_FOR_MERGE_FILTERS = Yes
    EXPOSED_ATTRIBUTE_LIST = surveyid,nrows_db
    FORMAT = POSTGRES
    SQL_STATEMENT = SELECT surveyid, count(*) nrows_db FROM dhs_data_tables."@Value(table_name)" GROUP BY surveyid
    COMBINE_ATTRS = Keep Result Attributes if Conflict
    RESULT -> FeatureMerger_2 [SUPPLIER]
Tester_3
    TEST_DESCRIPTION = ""
    BOOL_OP = OR
    TEST_CLAUSE = TEST @Value(RecordName_File) IN REC01,REC11,REC22
    TEST_MODE = Automatic
    PASSED -> FeatureMerger [REQUESTOR]
Note: Does this table already exist?
FeatureMerger
    ATTR_CONFLICT_RES = Use Requestor
    MERGE_TYPE = Attributes Only
    REJECT_NULL_MISSING_KEYS = No
    PROCESS_DUPS = No
    SUPPLIERS_FIRST = Yes
    IGNORE_NULLS = No
    ATTR_ACCUM_MODE = Merge Supplier
    JOIN_KEYS = @Value(RecordName_File) @Value(table_name) AUTO
    MERGED -> FeatureMerger_2 [REQUESTOR]
    NOT_MERGED -> AttributeCopier
    NOT_MERGED -> Table_Not_Yet_Begun
Note: Has this particualr survey table been loaded even partially?
FeatureMerger_2
    ATTR_CONFLICT_RES = Use Requestor
    MERGE_TYPE = Attributes Only
    REJECT_NULL_MISSING_KEYS = No
    PROCESS_DUPS = No
    SUPPLIERS_FIRST = Yes
    IGNORE_NULLS = No
    ATTR_ACCUM_MODE = Merge Supplier
    JOIN_KEYS = @Value(SurveyID_File) @Value(surveyid) AUTO @Value(RecordName_File) @Value(table_name) AUTO
    MERGED -> PythonCaller
    NOT_MERGED -> File_Adding_To_Table
    NOT_MERGED -> AttributeCopier
Note: Disable this connection to skip reloading files that are already partially loaded
Note: Get num lines in the CSV
PythonCaller
    NEW_ATTRIBUTES = nrows_file
    PYTHONSYMBOL = FeatureProcessor
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              with open (feature.getAttribute('path_windows')) as f:
                  for i,l in enumerate(f):
                      pass
              # nrows will be i+1 but we want to discard 1 (the header)
              feature.setAttribute("nrows_file", i)
              self.pyoutput(feature)
          def close(self):
              pass
    -> Tester_2
Note: Does the file have the same number of rows as the db?
Tester_2
    TEST_DESCRIPTION = ""
    BOOL_OP = OR
    TEST_CLAUSE = TEST @Value(nrows_file) = @Value(nrows_db)
    TEST_MODE = Automatic
    PASSED -> File_Already_Loaded
    FAILED -> Incomplete_Svy_Loaded
    FAILED -> SQLExecutor [INITIATOR]
Note: No ned to do anything
File_Already_Loaded: Inspector
Incomplete_Svy_Loaded: Inspector
Note: Drop data rows from part-loaded CSV and rerun it
SQLExecutor
    DATASET = Admin on MAP-FS1
    POSTGRES_NAMED_CONNECTION = Admin on MAP-FS1
    COMBINE_GEOM = Initiator Geometry Only
    POSTGRES_QUERY_FEATURE_TYPES_FOR_MERGE_FILTERS = Yes
    POSTGRES_SCHEMAS_FOR_TABLE_LISTING = dhs_data_tables
    FORMAT = POSTGRES
    SQL_STATEMENT = DELETE FROM  dhs_data_tables."@Value(table_name)" WHERE surveyid = '@Value(surveyid)'
    COMBINE_ATTRS = Keep Initiator Attributes if Conflict
    INITIATOR -> AttributeKeeper
File_Adding_To_Table: Inspector
Note: If not then we definitely want to load
AttributeCopier
    ATTR_TABLE:
      COPY RecordName_File > table_name
      COPY SurveyID_File > surveyid
    -> AttributeKeeper
Note: Collate all the files we want to load
AttributeKeeper
    KEEP_ATTRS = surveyid,path_windows,table_name
    -> FeatureMerger_3 [REQUESTOR]
Note: Disable this connection to skip loading whole new tables
Table_Not_Yet_Begun: Inspector
Note: Read the schemas of all the CSV files. This was pre-generated in a separate workbench or could be done on-the-fly
AllSchemas (reader FFS_1)
    attributes: RecordName varchar(7), attribute{}.name varchar(200), attribute{}.fme_data_type varchar(200), attribute{}.StartMin varchar(200)
    -> AttributeCreator
AttributeCreator
    ATTR_LIST = qualtablename,dhs_data_tables.@Value(RecordName)
    -> ListElementCounter
ListElementCounter
    LIST_NAME = attribute{}
    CNT_ATTR = _column_count
    -> Tester
Note: For tables with unwieldy schemas, we don't create them as is. We load them as JSONB data instead. The tables were first created as
Tester
    TEST_DESCRIPTION = ""
    BOOL_OP = AND
    TEST_CLAUSE = TEST @Value(_column_count) <= 1600
    TEST_MODE = Automatic
    PASSED -> FeatureMerger_3 [SUPPLIER]
    PASSED -> Normal_Tables
    FAILED -> JSON_Tables
Note: Get the schema of the table this file goes into: any one file (survey) for a given table may not have all the attribs needed, so load the schema separately. Also drop any CSVs we have chosen to skip below.
FeatureMerger_3
    ATTR_CONFLICT_RES = Use Requestor
    MERGE_TYPE = Attributes Only
    REJECT_NULL_MISSING_KEYS = No
    PROCESS_DUPS = No
    SUPPLIERS_FIRST = No
    IGNORE_NULLS = No
    ATTR_ACCUM_MODE = Merge Supplier
    JOIN_KEYS = @Value(table_name) @Value(RecordName) AUTO
    MERGED -> FeatureReader [INITIATOR]
    MERGED -> Files_To_Load_Normal
    NOT_MERGED -> AttributeCreator_2
Files_To_Load_Normal: Inspector
Note: Read the csv file. We don't know here the attributes it will have so they don't show here (and if they did there would be many thousand of them) but the dynamic writer will know what it is looking for.
FeatureReader
    CSV__FIELD_NAMES_AFTER_HEADER = no
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    CSV__STRIP_QUOTES = yes
    CSV__ALLOW_SPACES_IN_COLUMN_NAMES = yes
    FEATURETYPES_RADIO = FEATURETYPES
    FORMAT = CSV
    ATTRS_TO_EXPOSE = fme_basename
    ATTR_CONFLICT_RES = Use Result
    CSV__SKIP_LINES = 1
    CSV__IN_SEPARATOR = ,
    OUTPUT_FEATURES_DISPLAY = Based on Connections
    CSV__SCHEMA_WITH_COL_NAMES = name,char,12,,RecordName,char,6,,coltype,char,17,
    COMBINE_GEOM = Use Result
    CSV__SKIP_FOOTER = 0
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    ATTR_ACCUM_MODE = Merge Initiator and Result
    CSV__SCHEMA = char,12,,char,6,,char,17,
    CSV__IN_FIELD_NAMES = YES
    CSV__GROUP_BY_DATASET = no
    DATASET = @Value(path_windows)
    CSV__DUPLICATE_DELIMS = no
    CSV_SCAN_MAX_FEATURES = 1000
    <OTHER> -> NullAttributeMapper
Note: As we're reading from CSVs we have blank strings rather than proper nulls, so convert those. This is crucial for the many-column tables which contain the unioned set of all attribs across all surveys containing that table. Using null ensures all the empty cols only take 1 bit.
NullAttributeMapper
    ATTRCHOICE = All Attributes
    SOURCE_ATTR_VAL = Null Empty
    NULL_TREATMENT = Null
    -> Table1 (writer POSTGRES_1)
Table1 (writer POSTGRES_1)
AttributeCreator_2
    ATTR_LIST = qualtablename,dhs_data_tables.@Value(table_name)
    -> _largeTableFiles (writer CSV_1)
    -> Files_To_Load_JSON
Files_To_Load_JSON: Inspector
_largeTableFiles (writer CSV_1)
    attributes: path_windows text, table_name auto, surveyid auto, qualtablename auto
Normal_Tables: Inspector
JSON_Tables: Inspector
