FME workspace Load_Value_Specs_To_DB.fmw

Parameters:
- SourceDataset_CSV = \\map-fs1.ndph.ox.ac.uk\map_data\DHS_Automation\DataExtraction\All\ParsedSpecs\437*.FlatValuesSpec.csv   # Source CSV (Comma Separated Value) File(s)
- DestDataset_POSTGRES = Admin on MAP-FS1   # Connection
- SourceDataset_CSV_3 = \\map-fs1.ndph.ox.ac.uk\map_data\DHS_Automation\DataExtraction\All\ParsedSpecs\437*.FlatRecordSpec.csv   # Source CSV (Comma Separated Value) File(s)

Readers:
- CSV_1: CSV from $(SourceDataset_CSV)
- CSV_2: CSV from $(SourceDataset_CSV_3)

Writers:
- POSTGRES_1: POSTGRES to $(DestDataset_POSTGRES)

CSV (reader CSV_2) [off]
    attributes: ItemType char(17), FileCode char(11), RecordName char(7), RecordTypeValue char(4), RecordLabel char(50), Name char(12), Label char(107), Start number(4,0), Len number(3,0), Occurrences number(3,0), ZeroFill char(4), DecimalChar char(3), Decimal char(1), FMETYPE char(13)
    -> BulkAttributeRenamer
BulkAttributeRenamer [off]
    PATTERN_ACTION_DISP = CASECHANGE
    ATTRCHOICE = All Attributes
    CASE_CHANGE_TYPE = lower
    MODE_CHOICE = RENAME
    -> StringSearcher_2
StringSearcher_2 [off]
    REGEXP = ^\d+
    CASE = no
    MATCHED_RESULT_ATTR = surveyid
    STRING_TO_SEARCH = @Value(filecode)
    MATCHED -> SQLExecutor [INITIATOR]
SQLExecutor [off]
    SQL_STATEMENT:
      select name from dhs_survey_specs.dhs_table_specs_flat
      where
      surveyid = '@Value(surveyid)'
      AND
      recordname = '@Value(recordname)'
      AND
      name = '@Value(name)'
    COMBINE_GEOM = Initiator Geometry Only
    DATASET = DHS Data Readonly
    POSTGRES_QUERY_FEATURE_TYPES_FOR_MERGE_FILTERS = Yes
    POSTGRES_NAMED_CONNECTION = DHS Data Readonly
    FORMAT = POSTGRES
    COMBINE_ATTRS = Result Attributes Only
    INITIATOR -> Tester
Tester [off]
    TEST_MODE = Automatic
    TEST_CLAUSE = TEST @Value(_matched_records) = 0
    BOOL_OP = OR
    TEST_DESCRIPTION = ""
    PASSED -> AttributeCreator_2
    FAILED -> AttributeCreator
AttributeCreator_2 [off]
    ATTR_TABLE = SET_TO fme_db_operation = INSERT
    -> dhs_survey_specs.dhs_table_specs_flat (writer POSTGRES_1)
AttributeCreator [off]
    ATTR_TABLE = SET_TO fme_db_operation = UPDATE
    -> dhs_survey_specs.dhs_table_specs_flat (writer POSTGRES_1)
dhs_survey_specs.dhs_table_specs_flat (writer POSTGRES_1) [off]
    attributes: itemtype varchar(17), recordname varchar(20), recordtypevalue varchar(4), recordlabel varchar(85), name varchar(20), label varchar(200), start int2, len int2, fmetype varchar(13), surveyid varchar(4)
Note: Just dumps all the table and value specs into flat database tables. We have a separate relational structure set up for this schema information but that's not currently in use.
CSV (reader CSV_1)
    attributes: FileCode char(11), Name char(9), Value char(11), ValueDesc char(61), ValueType char(14)
    -> StringSearcher
StringSearcher
    REGEXP = ^\d+
    CASE = no
    MATCHED_RESULT_ATTR = surveyid
    STRING_TO_SEARCH = @Value(FileCode)
    MATCHED -> StringReplacer
StringReplacer
    REGEXP = NO
    FIND_TEXT = '
    CASE = NO
    SRC_ATTRS = Value
    NO_MATCH = _FME_NO_OP_
    -> AttributeTrimmer
AttributeTrimmer
    SRC_ATTRS = ValueDesc,Value
    TRIM_TYPE = Both
    TRIM_TO_NONE = Yes
    -> AttributeManager
AttributeManager
    ATTR_TABLE:
      REMOVE FileCode
      RENAME_SET_VALUE Name > col_name
      RENAME_SET_VALUE Value > value
      RENAME_SET_VALUE ValueDesc > value_desc
      RENAME_SET_VALUE ValueType > value_type
    -> NullAttributeMapper
NullAttributeMapper
    NULL_TREATMENT = Null
    ATTRCHOICE = Selected Attributes
    SOURCE_ATTR_VAL = Null Empty
    ATTRLIST = value_desc value_type
    -> dhs_survey_specs.dhs_value_descs (writer POSTGRES_1)
dhs_survey_specs.dhs_value_descs (writer POSTGRES_1)
    attributes: col_name varchar(20), value varchar(20), value_desc varchar(200), value_type varchar(20), surveyid varchar(4)
