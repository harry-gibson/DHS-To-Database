FME workspace Load_All_Cluster_Shapes_To_PG.fmw

Parameters:
- SourceDataset_ESRISHAPE = \\map-fs1.ndph.ox.ac.uk\map_data\DHS_Automation\Acquisition\All\**\*.shp   # Source Esri Shapefile(s)
- Points_DB_Connection = Admin on MAP-FS1   # DB for survey points
- FEATURE_TYPES =

Readers:
- ESRISHAPE_1: ESRISHAPE from $(SourceDataset_ESRISHAPE)

Writers:
- POSTGIS_1: POSTGIS to $(Points_DB_Connection)

Note: Loads DHS cluster locations (so-called "GPS data") to the DB
Note: Get survey IDs already in the database
SQLCreator
    POSTGIS_USE_TRUE_POSTGIS_TYPES = yes
    EXPOSED_ATTRIBUTE_LIST = surveyid
    POSTGIS_QUERY_FEATURE_TYPES_FOR_MERGE_FILTERS = Yes
    FORMAT = POSTGIS
    SQL_STATEMENT = select distinct surveyid from dhs_data_locations.dhs_cluster_locs
    POSTGIS_SCHEMAS_FOR_TABLE_LISTING = dhs_data_locations
    POSTGIS_NAMED_CONNECTION = $(Points_DB_Connection)
    DATASET = $(Points_DB_Connection)
    POSTGIS_DISABLE_COLLECTION_SPLITTING = yes
    RESULT -> Existing_Survey_IDs
    RESULT -> FeatureMerger [SUPPLIER]
Existing_Survey_IDs: Inspector
Note: Read all the shapefiles in and below the provided directory. We're assuming they all have the same schema
337.CMGE61FL (reader ESRISHAPE_1)
    attributes: DHSID char(254), DHSCC char(254), DHSYEAR number(16,0), DHSCLUST number(16,0), CCFIPS char(254), ADM1FIPS char(254), ADM1FIPSNA char(254), ADM1SALBNA char(254), ADM1SALBCO char(254), ADM1DHS number(16,0), ADM1NAME char(254), DHSREGCO number(16,0), DHSREGNA char(254), SOURCE char(254), URBAN_RURA char(254), LATNUM number(16,6), LONGNUM number(16,6), ALT_GPS number(16,0), ALT_DEM number(16,0), DATUM char(254)
    -> AttributeExposer
AttributeExposer
    ATTR_LIST = fme_basename,fme_dataset
    -> StringSearcher
StringSearcher
    STRING_TO_SEARCH = @Value(fme_basename)
    MATCHED_RESULT_ATTR = SurveyID
    REGEXP = ^\d+
    CASE = no
    MATCHED -> FeatureMerger [REQUESTOR]
    NOT_MATCHED -> Survey_ID_Not_Parsed
Note: Basic check: we just skip a shapefile if any points of that survey id already exist. Not taking any other action for now (like checking they're the same).
FeatureMerger
    PROCESS_DUPS = No
    SUPPLIERS_FIRST = No
    MERGE_TYPE = Attributes Only
    ATTR_CONFLICT_RES = Use Requestor
    JOIN_KEYS = @Value(SurveyID) @Value(surveyid) AUTO
    IGNORE_NULLS = No
    ATTR_ACCUM_MODE = Merge Supplier
    REJECT_NULL_MISSING_KEYS = No
    MERGED -> DuplicateFilter_2
    NOT_MERGED -> AttributeSplitter_2
    NOT_MERGED -> DuplicateFilter
DuplicateFilter_2
    INPUT_ORDERED_CHOICE = No
    KEYATTR = SurveyID
    UNIQUE -> Survey_Pts_Already_Present
Survey_Pts_Already_Present: Inspector
DuplicateFilter
    INPUT_ORDERED_CHOICE = No
    KEYATTR = SurveyID
    UNIQUE -> Points_Not_Present
Points_Not_Present: Inspector
AttributeSplitter_2
    ATTR_NAME = fme_feature_type
    DELIMITER = .
    TRIM_OPTION = Both
    LIST_NAME = _list
    DROP_EMPTY_PARTS = No
    -> ListIndexer_2
ListIndexer_2
    LIST_ATTR = _list{}
    INDEX = -1
    -> AttributeRenamer
    <REJECTED> -> ListIndexer_2__Rejected_
AttributeRenamer
    ATTR_TABLE = RENAME_SET_DEFAULT _list > ShapefileName
    -> BulkAttributeRenamer
BulkAttributeRenamer
    PATTERN_ACTION_DISP = CASECHANGE
    ATTRCHOICE = All Attributes
    MODE_CHOICE = RENAME
    CASE_CHANGE_TYPE = lower
    -> dhs_data_locations.dhs_cluster_locs (writer POSTGIS_1)
dhs_data_locations.dhs_cluster_locs (writer POSTGIS_1)
    attributes: dhsid varchar(80), surveyid int4, dhscc varchar(6), dhsyear int8, dhsclust int8, ccfips varchar(80), adm1fips varchar(80), adm1fipsna varchar(80), adm1salbna varchar(80), adm1salbco varchar(80), adm1dhs int8, adm1name varchar(80), dhsregco int8, dhsregna varchar(80), source varchar(20), urban_rura varchar(20), latnum numeric(16,6), longnum numeric(16,6), alt_gps int8, alt_dem int8, datum varchar(80), shapefilename varchar(10)
ListIndexer_2__Rejected_: Inspector
Survey_ID_Not_Parsed: Inspector
