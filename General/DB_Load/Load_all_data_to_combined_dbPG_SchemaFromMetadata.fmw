FME workspace Load_all_data_to_combined_dbPG_SchemaFromMetadata.fmw

Parameters:
- DestDataset_POSTGRES = mapprod1-dev-dhsdata   # Connection
- SourceDataset_FFS = \\map-fs1.ndph.ox.ac.uk\map_data\DHS_Automation\DataExtraction\All\PG_Database_Load\All_Combined_Table_Schemas_FromMetadata.ffs   # Source FME Feature Store (FFS) File(s)
- ProcessedTableDir = \\map-fs1.ndph.ox.ac.uk\map_data\DHS_Automation\DataExtraction\All\ProcessedTables   # Directory containing all processed table CSVs

Readers:
- FFS_1: FFS from $(SourceDataset_FFS)

Writers:
- POSTGRES_1: POSTGRES to $(DestDataset_POSTGRES)

AllSchemas (reader FFS_1)
    attributes: RecordName varchar(7), attribute{}.name varchar(200), attribute{}.fme_data_type varchar(200), attribute{}.StartMin varchar(200)
    -> AttributeCreator_2
AttributeCreator_2
    ATTR_TABLE = SET_TO _reqSurveyFile = $(ProcessedTableDir)\*.@Value(RecordName).csv
    -> AttributeCreator
AttributeCreator
    ATTR_LIST = qualtablename,dhs_data_tables.@Value(RecordName)
    -> ListElementCounter
ListElementCounter
    CNT_ATTR = _element_count
    LIST_NAME = attribute{}
    -> Tester
Tester
    TEST_DESCRIPTION = ""
    BOOL_OP = AND
    TEST_MODE = Automatic
    TEST_CLAUSE:
      TEST @Value(_element_count) <= 1000
      TEST @Value(RecordName) != RECH6
      TEST @Value(_element_count) > 100
    PASSED -> FeatureMerger [REQUESTOR]
    FAILED -> Not_Running_This_Time
Not_Running_This_Time: Inspector
Note: This workbench loads ALL DHS survey data from the CSV files (a file for every table and every survey) to a database with one table per overall table / recordtype, each containing data from all the surveys. / The schema of these DB tables has been calculated in advance to contain the union of all the surveys' columns for that record type. The schema definitions are read in using a workspace resource from a CSV file. / Note that we don't do anything in this loader about creating indexes. We'll have to do that in code later.
SQLCreator
    EXPOSED_ATTRIBUTE_LIST = table_name
    POSTGRES_SCHEMAS_FOR_TABLE_LISTING = dhs_data_tables
    DATASET = mapprod1-dev-dhsdata
    FORMAT = POSTGRES
    SQL_STATEMENT:
      SELECT table_name
      FROM information_schema.tables
      WHERE table_name LIKE 'REC%'
    POSTGRES_NAMED_CONNECTION = mapprod1-dev-dhsdata
    POSTGRES_QUERY_FEATURE_TYPES_FOR_MERGE_FILTERS = Yes
    RESULT -> FeatureMerger [SUPPLIER]
FeatureMerger
    PROCESS_DUPS = No
    ATTR_CONFLICT_RES = Use Requestor
    MERGE_TYPE = Attributes Only
    SUPPLIERS_FIRST = No
    IGNORE_NULLS = No
    ATTR_ACCUM_MODE = Merge Supplier
    JOIN_KEYS = @Value(RecordName) @Value(table_name) AUTO
    REJECT_NULL_MISSING_KEYS = No
    MERGED -> Table_Already_Exists
    NOT_MERGED -> To_Be_Created
    NOT_MERGED -> FeatureReader [INITIATOR]
Table_Already_Exists: Inspector
To_Be_Created: Inspector
Note: Read the csv file. We don't know here the attributes it will have so they don't show here (and if they did there would be many thousand of them) but the dynamic writer will know what it is looking for.
FeatureReader
    CSV_SCAN_MAX_FEATURES = 1000
    ATTR_CONFLICT_RES = Use Result
    FORMAT = CSV
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    DATASET = @Value(_reqSurveyFile)
    CSV__IN_SEPARATOR = ,
    CSV__DUPLICATE_DELIMS = no
    CSV__GROUP_BY_DATASET = no
    OUTPUT_FEATURES_DISPLAY = Based on Connections
    FEATURETYPES_RADIO = FEATURETYPES
    CSV__SKIP_FOOTER = 0
    CSV__STRIP_QUOTES = yes
    CSV__SCHEMA = char,12,,char,6,,char,17,
    CSV__IN_FIELD_NAMES = YES
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__ALLOW_SPACES_IN_COLUMN_NAMES = yes
    CSV__SKIP_LINES = 1
    ATTRS_TO_EXPOSE = fme_basename
    CSV__SCHEMA_WITH_COL_NAMES = name,char,12,,RecordName,char,6,,coltype,char,17,
    CSV__FIELD_NAMES_AFTER_HEADER = no
    ATTR_ACCUM_MODE = Merge Initiator and Result
    COMBINE_GEOM = Use Result
    <OTHER> -> StringSearcher
StringSearcher
    STRING_TO_SEARCH = @Value(fme_basename)
    CASE = no
    REGEXP = ^\d+
    MATCHED_RESULT_ATTR = SurveyID
    MATCHED -> NullAttributeMapper
    MATCHED -> StringSearcher_NotMatched [off]
StringSearcher_NotMatched: Inspector
Note: As we're reading from CSVs we have blank strings rather than proper nulls, so convert those
NullAttributeMapper
    NULL_TREATMENT = Null
    ATTRCHOICE = All Attributes
    SOURCE_ATTR_VAL = Null Empty
    -> Table1 (writer POSTGRES_1)
Table1 (writer POSTGRES_1)
