FME workspace Load_JSON_large_table_data_to_combined_dbPG.fmw

Parameters:
- DestDataset_POSTGRES = Admin on MAP-FS1 (DHS instance)   # Connection
- File_Listing = E:\Data\Harry\Documents\dataprep\DHS_Updates\update_logs\_largeTableFiles_bak.csv   # CSV listing the csv tables that should be loaded as JSON
- SourceDataset_POSTGRES_2 = Admin on MAP-FS1 (DHS instance)   # Connection
- SourceDataset_CSV2 = C:\Temp\rech4_need_loading_json.csv   # Source CSV (Comma Separated Value) File(s)

Readers:
- CSV_1: CSV from $(File_Listing)
- POSTGRES_1: POSTGRES from $(SourceDataset_POSTGRES_2)
- CSV2_1: CSV2 from $(SourceDataset_CSV2)

Writers:
- POSTGRES_2: POSTGRES to $(DestDataset_POSTGRES)

CSV (reader CSV2_1)
    attributes: surveyid string, path_windows string, table_name string, qualtablename string
    -> AttributeRenamer
AttributeRenamer
    ATTR_TABLE:
      RENAME_SET_DEFAULT path_windows > _CSV_file_name
      RENAME_SET_DEFAULT qualtablename > _qual_tbl_name
    -> AttributeExposer_2
AttributeExposer_2
    ATTR_LIST = csv_line_number,csv_number_of_fields,csv_total_number_of_columns,csv_type,multi_reader_full_id,multi_reader_id,multi_reader_keyword,multi_reader_type
    -> AttributeRemover_2
AttributeRemover_2
    REMOVE_ATTRS = csv_line_number,multi_reader_type,csv_number_of_fields,multi_reader_full_id,multi_reader_id,multi_reader_keyword,csv_total_number_of_columns,csv_type
    -> SQLExecutor_2 [INITIATOR]
Note: Get the number of rows already existing for each survey in the DB table
SQLExecutor_2
    COMBINE_ATTRS = Keep Result Attributes if Conflict
    COMBINE_GEOM = Initiator Geometry Only
    DATASET = DHS Data Readonly
    EXPOSED_ATTRIBUTE_LIST = nrows_db
    FORMAT = POSTGRES
    POSTGRES_NAMED_CONNECTION = DHS Data Readonly
    POSTGRES_QUERY_FEATURE_TYPES_FOR_MERGE_FILTERS = Yes
    SQL_STATEMENT = SELECT count(*) nrows_db FROM dhs_data_tables."@Value(table_name)" WHERE surveyid = '@Value(surveyid)'
    RESULT -> Tester
    <REJECTED> -> SQLExecutor_2__Rejected_
Note: For now we'll just skip any that are already there
Tester
    BOOL_OP = OR
    TEST_CLAUSE = TEST @Value(nrows_db) = 0
    PASSED -> FeatureReader_2 [INITIATOR]
    FAILED -> Already_Partly_In_DB
Already_Partly_In_DB: Inspector
Note: Read the csv file. We don't know here the attributes it will have so they don't show here but the attribute-json packer will find and pack them nonetheless
FeatureReader_2
    ATTRS_TO_EXPOSE = fme_basename CASEID HHID SQUESTID
    ATTR_ACCUM_MODE = Merge Initiator and Result
    ATTR_CONFLICT_RES = Use Result
    COMBINE_GEOM = Use Result
    CSV_SCAN_MAX_FEATURES = 1000
    CSV__ALLOW_SPACES_IN_COLUMN_NAMES = yes
    CSV__DUPLICATE_DELIMS = no
    CSV__ENCODING = utf-8
    CSV__FIELD_NAMES_AFTER_HEADER = no
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    CSV__GROUP_BY_DATASET = no
    CSV__IN_FIELD_NAMES = YES
    CSV__IN_SEPARATOR = ,
    CSV__SCHEMA = char,12,,char,6,,char,17,
    CSV__SCHEMA_WITH_COL_NAMES = name,char,12,,RecordName,char,6,,coltype,char,17,
    CSV__SKIP_FOOTER = 0
    CSV__SKIP_LINES = 1
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__STRIP_QUOTES = yes
    DATASET = @Value(_CSV_file_name)
    FEATURETYPES_RADIO = FEATURETYPES
    FORMAT = CSV
    OUTPUT_FEATURES_DISPLAY = Based on Connections
    <OTHER> -> BulkAttributeRenamer
BulkAttributeRenamer
    ATTRCHOICE = All Attributes
    CASE_CHANGE_TYPE = lower
    MODE_CHOICE = RENAME
    PATTERN_ACTION_DISP = CASECHANGE
    -> AttributeRemover
Note: Remove some stuff we don't want going into the JSON attribute
AttributeRemover
    REMOVE_ATTRS = _creation_instance,fme_basename,path_windows,_csv_file_name
    -> AttributeJSONPacker_2
Note: Pack all the non-ID attributes into a single JSON attribute. This custom transformer was downloaded from FME store and then modified to allow specification of attributes or wildcards to skip, as well as to include
AttributeJSONPacker_2
    FILTEREXC = idx
    PACKED = data
    SKIPATTRS = hhid,nrows_db,surveyid,table_name,_qual_tbl_name,caseid,squestid
    -> AttributeExposer
AttributeExposer
    ATTR_LIST = data
    -> REC91 (writer POSTGRES_2)
Note: Load to tables that have been (manually) precreated to / include the correct index columns for this table plus a single jsonb data column. These tables have been added as a workspace resource so the dynamic writer knows the ID columns to write.
REC91 (writer POSTGRES_2)
    attributes: surveyid varchar(3), data text
SQLExecutor_2__Rejected_: Inspector
CSV (reader CSV_1) [off]
    attributes: path_windows char(104), table_name char(6), surveyid number(4,0), qualtablename char(22)

FME custom transformer AttributeJSONPacker
This transformer packs all the attributes that are chosen, or fit the user filter, into a single attribute, as a dictionary in a JSON compatible format:
{"PRI":"2","COMMENTS":"Test Data"}
This is useful for storing multiple format attributes in a single database field for future conversions back to the original format. 
Binary attributes will be hex-encoded and prefaced with "0x". 
Packed attributes can be unpacked using the AttributeJSONUnpacker transformer.
Input Ports
    Input
Accepts any feature.
    Output Ports
    Output
Ouputs the original feature with an added attribute containing the JSON object.
    Parameters
    Attributes to Pack
    Specific attributes to pack. Chosing any attributes will disable the filter (described below).
    Filter Prefix
All attributes with this prefix will be added to the packed attribute. Leaving this value blank will pack all the attributes.
    Packed Attribute Name
The name of the new attribute containing the packed values

Parameters:
- FILTER =   # Filter Prefix to INCLUDE (blank for all attributes)
- PACKED = _packed   # Packed Attribute Name
- ATTRS =   # " " Attributes to Pack
- SKIPATTRS =   # " " Attributes to Skip Packing
- FILTEREXC =   # Filter to EXCLUDE attributes (blank to not use)

Input (input)
    -> ParameterFetcher
Note: Get filter value
ParameterFetcher
    ATTR_LIST = AttributeJSONPacker_FILTER {$(FILTER)} AttributeJSONPacker_PACKED {$(PACKED)} AttributeJSONPacker_ATTRS {$(ATTRS)} AttributeJSONPacker_SKIPATTRS {$(SKIPATTRS)} AttributeJSONPacker_FILTEREXC {$(FILTEREXC)}
    -> PythonCaller
PythonCaller
    NEW_ATTRIBUTES = $(PACKED)
    PYTHONSOURCE:
      import fmeobjects
      import binascii
      import json

      # This class will create a packed list of format
      # attributes suitable for use with @SupplyAttributes()

      def packIgdsAtts(feature):

         # get a list of attribute names
         attlist = feature.getAllAttributeNames()
         attlist = map(unicode, attlist)

         # get attributes to pack
         pack_attrs = feature.getAttribute('AttributeJSONPacker_ATTRS').replace('"', '').strip().split(',')

         skip_attrs = feature.getAttribute('AttributeJSONPacker_SKIPATTRS').replace('"', '').strip().split(',')

         # get filter value
         filter = feature.getAttribute('AttributeJSONPacker_FILTER')
         filterExc = feature.getAttribute('AttributeJSONPacker_FILTEREXC')

         # get packed attribute name
         packedAtt = feature.getAttribute('AttributeJSONPacker_PACKED')

         # disable filter if packed attribute chosen
         if pack_attrs[0] != "":
             filter = '########################################################################'

         # create list for packed attributes
         packed = {}

         # loop through attribute names
         for att in attlist:
             if ((filter in att or att in pack_attrs) and (not att in skip_attrs) and
                  (not filterExc in att) and
                  att != 'AttributeJSONPacker_ATTRS' and
                  att != 'AttributeJSONPacker_FILTER' and
                  att != 'AttributeJSONPacker_PACKED' and
                  att != 'AttributeJSONPacker_SKIPATTRS' and
                  att != 'AttributeJSONPacker_FILTEREXC' and
                  not att.startswith('fme') and
                  not att.startswith('csv')):
                 att_value = feature.getAttribute(att)
                 # convert binary attributes to hex for storage
                 if type(att_value) == bytearray:
                     att_value = "0x" + binascii.hexlify(att_value)
                 # append attribute value
                 packed[att] = att_value

         #add packed attributes in JSON format
         feature.setAttribute(packedAtt,json.dumps(packed,separators=(',', ':'), ensure_ascii=False))
    PYTHONSYMBOL = packIgdsAtts
    -> Output (output)
Output (output)
