FME workspace load_cluster_points.fmw

Parameters:
- SourceDataset_SHAPE = \\129.67.26.176\map_data\DHS_Automation\Acquisition\20150626_FullSiteScrape\downloads\**\*.shp   # Source Esri Shape File(s)
- FEATURE_TYPES =
- DestDataset_POSTGIS = admin@map.zoo.ox.ac.uk:5434/arcgis_pit   # Connection

Readers:
- SHAPE_1: SHAPE from $(SourceDataset_SHAPE)

Writers:
- POSTGIS_1: POSTGIS to $(DestDataset_POSTGIS)

337.CMGE61FL (reader SHAPE_1)
    attributes: DHSID char(254), DHSCC char(254), DHSYEAR number(16,0), DHSCLUST number(16,0), CCFIPS char(254), ADM1FIPS char(254), ADM1FIPSNA char(254), ADM1SALBNA char(254), ADM1SALBCO char(254), ADM1DHS number(16,0), ADM1NAME char(254), DHSREGCO number(16,0), DHSREGNA char(254), SOURCE char(254), URBAN_RURA char(254), LATNUM number(16,6), LONGNUM number(16,6), ALT_GPS number(16,0), ALT_DEM number(16,0), DATUM char(254)
    -> CoordinateExtractor
    -> AttributeExposer
CoordinateExtractor
    Y_ATTR = _y
    Z_DEFAULT = -9999
    X_ATTR = _x
    IND = 0
    Z_ATTR = _z
    -> Tester
Tester
    TEST_MODE = Automatic
    BOOL_OP = AND
    TEST_CLAUSE:
      TEST @Evaluate(@abs(@Value(_x)-@Value(LONGNUM))<0.01) = 1
      TEST @Evaluate(@abs(@Value(_y)-@Value(LATNUM))<0.01) = 1
    TEST_DESCRIPTION = ""
    PASSED -> Tester_Passed
    FAILED -> Tester_Failed
Tester_Passed: Inspector
Tester_Failed: Inspector
AttributeExposer
    ATTR_LIST = fme_feature_type
    -> StringSearcher
StringSearcher
    STRING_TO_SEARCH = @Value(fme_feature_type)
    MATCHED_RESULT_ATTR = svyID
    CASE = no
    MATCHED_PARTS_ATTR = _matched_parts
    REGEXP = ^\d+
    MATCHED -> AttributeKeeper
    MATCHED -> BulkAttributeRenamer_2
BulkAttributeRenamer_2
    CASE_CHANGE_TYPE = lowercase
    ATTRCHOICE = All Attributes
    PATTERN_ACTION_DISP = Change Case
    -> dhs_cluster_points (writer POSTGIS_1)
dhs_cluster_points (writer POSTGIS_1)
    attributes: svyid int8, dhsid char(254), dhscc char(254), dhsyear float8, dhsclust float8, ccfips char(254), adm1fips char(254), adm1fipsna char(254), adm1salbna char(254), adm1salbco char(254), adm1dhs float8, adm1name char(254), dhsregco float8, dhsregna char(254), source char(254), urban_rura char(254), latnum float8, longnum float8, alt_gps float8, alt_dem float8, datum char(254)
AttributeKeeper
    KEEP_ATTRS = ADM1DHS,ADM1NAME,DHSCC,DHSCLUST,DHSID,DHSREGCO,DHSREGNA,LATNUM,LONGNUM,SOURCE,svyID,URBAN_RURA
    -> BulkAttributeRenamer
BulkAttributeRenamer
    ATTRCHOICE = All Attributes
    REPLACE_STR = Spatial_
    PATTERN_ACTION_DISP = Add String Prefix
