FME workspace Load_all_data_to_combined_dbSQLite_Spatialite.fmw

Parameters:
- SourceDataset_SCHEMA_FROM_TABLE = $(FME_MF_DIR)AllSchemas_Flat_NoGeom.csv   # Source Dataset
- SourceDataset_PATH = G:\DataPrep\DHS_Tables   # Source Folder and File Pathnames Folder
- DestDataset_SPATIALITE = $(FME_MF_DIR)All_DHS_Spatialite.db   # Destination SpatiaLite Database File

Readers:
- SCHEMA_FROM_TABLE_1: SCHEMA_FROM_TABLE from $(SourceDataset_SCHEMA_FROM_TABLE)
- PATH_1: PATH from $(SourceDataset_PATH)

Writers:
- SPATIALITE_1: SPATIALITE to $(DestDataset_SPATIALITE)

Note: This workbench loads ALL DHS survey data from the CSV files (a file for every table of every survey) to a database with one table per overall table / recordtype, each containing data from all the surveys. / The schema of these DB tables has been calculated in advance to contain the union of all the surveys' columns for that record type (because for a given table, not all surveys contain all the columns). The schema definitions are read in using a workspace resource from a CSV file. / Note that we don't do anything in this loader about creating indexes. We'll have to do that in code later.
PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> StringSearcher_2
StringSearcher_2
    REGEXP = ^(\d+)\.(\w+)\.(.+)$
    MATCHED_RESULT_ATTR = _matched_characters
    CASE = no
    STRING_TO_SEARCH = @Value(path_rootname)
    MATCHED_PARTS_ATTR = _
    MATCHED -> ListIndexer
ListIndexer
    PREFIX = SurveyID
    INDEX = 0
    LIST_ATTR = _{}
    -> ListIndexer_2
ListIndexer_2
    PREFIX = RecordName
    INDEX = 2
    LIST_ATTR = _{}
    -> AttributeRenamer
AttributeRenamer
    ATTR_LIST = RecordName_,tablename,,SurveyID_,SurveyID,
    -> Tester
Note: Don't load data from the country-specific tables as these have vast numbers of columns due to their being different in each survey. / (e.g. REC91 would have 14007 columns!!) / If we want to do anything with those data we'd have to restructure for storage in a single attr name / value table?
Tester
    BOOL_OP = AND
    TEST_MODE = Automatic
    TEST_DESCRIPTION = ""
    TEST_CLAUSE = TEST @Value(tablename) NOT_IN REC91,REC95,RECH3,REC94,REC97,REC98,RECH4,RECH8,REC99,RECH7,RECHG2
    PASSED -> Sorter
Sorter
    SORT_PARM = path_rootname ALPHA ASCENDING
    SORTED -> FeatureReader
Note: Read the csv file. We don't know here the attributes it will have so they don't show here (and if they did there would be many thousand of them) but the dynamic writer will know what it is looking for.
FeatureReader
    COMBINE_GEOM = Use Result
    CSV__ALLOW_SPACES_IN_COLUMN_NAMES = yes
    ATTR_ACCUM_MODE = Merge Initiator and Result
    CSV__IN_SEPARATOR = ,
    CSV__SKIP_LINES = 1
    FORMAT = CSV
    FEATURETYPES_RADIO = FEATURETYPES
    CSV__IN_FIELD_NAMES = YES
    CSV__GROUP_BY_DATASET = no
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    ATTR_CONFLICT_RES = Use Result
    CSV__FIELD_NAMES_AFTER_HEADER = no
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__STRIP_QUOTES = yes
    OUTPUT_FEATURES_DISPLAY = Based on Connections
    CSV__DUPLICATE_DELIMS = no
    CSV_SCAN_MAX_FEATURES = 1000
    CSV__SCHEMA = char,12,,char,6,,char,17,
    CSV__SKIP_FOOTER = 0
    DATASET = @Value(path_windows)
    CSV__SCHEMA_WITH_COL_NAMES = name,char,12,,RecordName,char,6,,coltype,char,17,
    <OTHER> -> NullAttributeMapper
Note: As we're reading from CSVs we have blank strings rather than proper nulls, so convert those
NullAttributeMapper
    SOURCE_ATTR_VAL = Null Empty
    NULL_TREATMENT = Null
    ATTRCHOICE = All Attributes
    -> table1 (writer SPATIALITE_1)
Note: Load to the database using schemas that have been pre-created by a separate workbench. The schema definitions are loaded to this WB from a CSV file which has been added as a workspace resource. / This ensures that each recordtype table is created using all the columns that are found in that recordtype for ANY survey
table1 (writer SPATIALITE_1)
