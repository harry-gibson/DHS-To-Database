FME workspace Load_all_data_to_combined_dbPG.fmw

Parameters:
- SourceDataset_SCHEMA_FROM_TABLE = $(FME_MF_DIR)AllSchemas_Flat_NoCal_TextType.csv   # Source Dataset
- SourceDataset_PATH = G:\DataPrep\DHS_Tables   # Source Folder and File Pathnames Folder
- DestDataset_POSTGRES = staging@map.zoo.ox.ac.uk:5434/dhs_data_pit   # Connection

Readers:
- SCHEMA_FROM_TABLE_1: SCHEMA_FROM_TABLE from $(SourceDataset_SCHEMA_FROM_TABLE)
- PATH_1: PATH from $(SourceDataset_PATH)

Writers:
- POSTGRES_1: POSTGRES to $(DestDataset_POSTGRES)

Note: This workbench loads ALL DHS survey data from the CSV files (a file for every table and every survey) to a database with one table per overall table / recordtype, each containing data from all the surveys. / The schema of these DB tables has been calculated in advance to contain the union of all the surveys' columns for that record type. The schema definitions are read in using a workspace resource from a CSV file. / Note that we don't do anything in this loader about creating indexes. We'll have to do that in code later.
PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> StringSearcher_2
StringSearcher_2
    STRING_TO_SEARCH = @Value(path_rootname)
    REGEXP = ^(\d+)\.(\w+)\.(.+)$
    CASE = no
    MATCHED_PARTS_ATTR = _
    MATCHED_RESULT_ATTR = _matched_characters
    MATCHED -> ListIndexer
ListIndexer
    LIST_ATTR = _{}
    PREFIX = SurveyID
    INDEX = 0
    -> ListIndexer_2
ListIndexer_2
    LIST_ATTR = _{}
    PREFIX = RecordName
    INDEX = 2
    -> AttributeRenamer
AttributeRenamer
    ATTR_LIST = RecordName_,tablename,,SurveyID_,SurveyID,
    -> Tester
Note: Don't load data from the country-specific tables as these have vast numbers of columns due to their being different in each survey. / (e.g. REC91 would have 14007 columns!!) / If we want to do anything with those data we'd have to restructure for storage in a single attr name / value table? / Also, during testing, filter to a particular survey here
Tester
    BOOL_OP = AND
    TEST_DESCRIPTION = ""
    TEST_MODE = Automatic
    TEST_CLAUSE:
      TEST @Value(tablename) NOT_IN REC91,REC95,RECH3,REC94,REC97,REC98,RECH4,RECH8,REC99,RECH7,RECHG2,REC82
      TEST @Value(SurveyID) NOT_= 222
    PASSED -> AttributeCreator
AttributeCreator
    ATTR_LIST = qualtablename,dhs_data_tables.@Value(tablename)
    -> FeatureReader
Note: Read the csv file. We don't know here the attributes it will have so they don't show here (and if they did there would be many thousand of them) but the dynamic writer will know what it is looking for.
FeatureReader
    ATTR_CONFLICT_RES = Use Result
    CSV__DUPLICATE_DELIMS = no
    ATTR_ACCUM_MODE = Merge Initiator and Result
    FORMAT = CSV
    CSV__STRIP_QUOTES = yes
    OUTPUT_FEATURES_DISPLAY = Based on Connections
    CSV__SKIP_LINES = 1
    CSV__GROUP_BY_DATASET = no
    FEATURETYPES_RADIO = FEATURETYPES
    CSV__IN_FIELD_NAMES = YES
    DATASET = @Value(path_windows)
    CSV__ALLOW_SPACES_IN_COLUMN_NAMES = yes
    CSV_SCAN_MAX_FEATURES = 1000
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES %\"%%\"Filter\"%\"STRING_ENCODED _FILTER_REGEX \"%%\"Invert Filter\"%\"CHECKBOX _FILTER_UNMATCHED yes%no\"%no"
    CSV__IN_SEPARATOR = ,
    COMBINE_GEOM = Use Result
    CSV__SCHEMA = char,12,,char,6,,char,17,
    CSV__SCHEMA_WITH_COL_NAMES = name,char,12,,RecordName,char,6,,coltype,char,17,
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES %\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__SKIP_FOOTER = 0
    CSV__FIELD_NAMES_AFTER_HEADER = no
    <OTHER> -> NullAttributeMapper
Note: As we're reading from CSVs we have blank strings rather than proper nulls, so convert those
NullAttributeMapper
    ATTRCHOICE = All Attributes
    NULL_TREATMENT = Null
    SOURCE_ATTR_VAL = Null Empty
    -> Table1 (writer POSTGRES_1)
Note: Load to the database using schemas that have been pre-created by a separate workbench. The schema definitions are loaded to this WB from a CSV file which has been added as a workspace resource. / This ensures that each recordtype table is created using all the columns that are found in that recordtype for ANY survey
Table1 (writer POSTGRES_1)
