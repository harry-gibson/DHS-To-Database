FME workspace merge_table_schemas_from_metadata.fmw

Parameters:
- SourceDataset_CSV = \\map-fs1.ndph.ox.ac.uk\map_data\DHS_Automation\Acquisition\All_MR\parsed\*.FlatRecordSpec.csv   # Source CSV (Comma Separated Value) File(s)
- DestDataset_FFS = \\map-fs1.ndph.ox.ac.uk\map_data\DHS_Automation\Acquisition\All_MR\pg_database_load\MR_Initial_Combined_Table_Schemas_FromMetadata.ffs   # Destination FME Feature Store (FFS) File

Readers:
- CSV_1: CSV from $(SourceDataset_CSV)

Writers:
- FFS_1: FFS to $(DestDataset_FFS)

CSV (reader CSV_1)
    attributes: ItemType char(17), SurveyIDDataColumnName char(9), SurveyID number(4,0), FileCode char(11), RecordName char(7), RecordTypeValue char(4), RecordLabel char(45), NameColumnName char(5), Name char(12), Label char(97), Start number(4,0), Len number(3,0), Occurrences number(3,0), ZeroFill char(4), DecimalChar char(3), Decimal char(1), FMETYPE char(13)
    -> StatisticsCalculator
StatisticsCalculator
    STATS_ATTRS = Len Start
    MIN_ATTR = Min
    MAX_ATTR = Max
    PREPEND_ATTR_NAME_CHOICE = For multiple results only
    GROUP_BY = Name RecordName
    COMPUTE_HISTOGRAM = NO
    SUMMARY -> AttributeManager
Note: Calculate what the schemas for the database tables should be. For every table (e.g. RECH1) reads the schema for that table for every survey. Creates the unioned set of column names, each of which is given the maximum width value it takes in any of the surveys. Writes the information to an FFS file as a list attribute which is suitable for use with a dynamic writer. / This is assuming we are storing data in tables that have all the columns in a "traditional" form. Note that this may not be feasible for some tables whose schema varies between surveys where the unioned set may be many hundreds or even thousands of columns. We will need to store those tables in a jsonb column; in fact there may be an argument for doing that for all tables.
AttributeManager
    ATTR_TABLE:
      RENAME_SET_VALUE Name > name
      SET_TO fme_data_type = fme_varchar(@Value(Len.Max))
      REMOVE Len.Min
      REMOVE Len.Max
      RENAME_SET_VALUE Start.Min > StartMin
      REMOVE Start.Max
    -> ListBuilder
    -> DuplicateFilter
DuplicateFilter
    KEYATTR = RecordName
    INPUT_ORDERED_CHOICE = No
    UNIQUE -> AttributeKeeper
AttributeKeeper
    KEEP_ATTRS = RecordName
    -> AttributeCreator
AttributeCreator
    ATTR_TABLE:
      SET_TO name = SurveyID
      SET_TO fme_data_type = fme_varchar(3)
      SET_TO StartMin = -1
    -> ListBuilder
ListBuilder
    LIST_NAME = attribute
    GRP_BY = RecordName
    -> ListSorter
ListSorter
    ORDER = Ascending
    TYPE = Numeric
    SRC_LIST = attribute{}.StartMin
    -> AttributeRemover
AttributeRemover
    LIST_ATTRS = attribute{}.RecordName
    -> AllSchemas (writer FFS_1)
    -> AttributeRemover_Output
    -> ListElementCounter
AttributeRemover_Output: Inspector
AllSchemas (writer FFS_1)
    attributes: RecordName varchar(7), attribute{}.name varchar(200), attribute{}.fme_data_type varchar(200), attribute{}.StartMin varchar(200)
ListElementCounter
    CNT_ATTR = _element_count
    LIST_NAME = attribute{}
    -> ListElementCounter_Output
ListElementCounter_Output: Inspector
