FME workspace Query_Indicator_API_PoC.fmw

Parameters:
- IndicatorID = 84275002   # Numeric Indicator ID
- DestDataset_CSV = $(FME_MF_DIR)Results   # Destination CSV (CommaSeparatedValue) Folder
- DestDataset_OGCKML = $(FME_MF_DIR)Results   # Destination Google KML File
- SourceDataset_SHAPE = C:\Users\zool1301\Documents\DHS\DHS_Info\dhs_subnational_boundaries_all_avail_surveys.shp   # Source Esri Shape File(s)

Readers:
- SHAPE_1: SHAPE from $(SourceDataset_SHAPE)

Writers:
- CSV_1: CSV to $(DestDataset_CSV)
- OGCKML_1: OGCKML to $(DestDataset_OGCKML)

Note: Create 100 features, this will allow us to make up to 100 requests and the API returns max 1000 features per page
Creator
    NUM = 100
    GEOMTYPE = Geometry Object
    CREATED -> ParameterFetcher
Note: As looping is not easily possible in FME (it is within a custom transformer, but that's a little more complicated) it would be difficult to find out how many pages of results there are and load them all. So here we take an alternative approach by preparing a large upper-bound number of queries, and only running them if their index is less than the number of pages available.
ParameterFetcher
    ATTR_LIST = _IndicatorID {$(IndicatorID)}
    -> AttributeCreator
AttributeCreator
    ATTR_LIST = _Page,@Evaluate(@Value(_creation_instance)+1)
    -> AttributeCreator_2
AttributeCreator_2
    ATTR_LIST = _URLTemplate,http://api.dhsprogram.com/rest/dhs/data/{IndID}?perpage=1000&breakdown=subnational&page={PageNum}
    -> AttributeCopier
AttributeCopier
    ATTR_LIST = _URLTemplate,_URL,
    -> StringReplacer
StringReplacer
    CASE = no
    REPLACE_TEXT = @Value(_IndicatorID)
    SRC_ATTRS = _URL
    REGEXP = no
    NO_MATCH = _FME_NO_OP_
    FIND_TEXT = {IndID}
    -> StringReplacer_2
StringReplacer_2
    CASE = no
    REPLACE_TEXT = @Value(_Page)
    SRC_ATTRS = _URL
    REGEXP = no
    NO_MATCH = _FME_NO_OP_
    FIND_TEXT = {PageNum}
    -> Sampler
Note: PoC could mean Proof of Concept. / Or it could mean Piece of Crap.
Sampler
    RATE = 1
    SAMPLE_TYPE_LONG = First N Features
    SAMPLED -> FeatureReader
    NOT_SAMPLED -> FeatureMerger_2 [input 1]
Note: Query the first page (<= 1000 results) from the DHS API
Note: Indicator ID examples: / 70254002 - U5M / 211493001 - fever in last 2 weeks
FeatureReader
    FORMAT = TEXTLINE
    ATTR_CONFLICT_RES = Use Result
    FEATURETYPES_RADIO = FEATURETYPES
    OUTPUT_FEATURES_DISPLAY = Based on Connections
    TEXTLINE_READ_WHOLE_FILE_AT_ONCE = YES
    DATASET = @Value(_URL)
    ATTRS_TO_EXPOSE = text_line_data
    ATTR_ACCUM_MODE = Merge Initiator and Result
    COMBINE_GEOM = Use Result
    <OTHER> -> JSONFragmenter_2
    <OTHER> -> JSONFragmenter_3
Note: Get the total number of pages that are available
JSONFragmenter_3
    EXPLODE_FORMAT = JSON
    JSON_QUERY = json["TotalPages"]
    PREF_STRING = TotalPages
    NEW_ATTRIBUTES = TotalPages
    EXTRACT_ATTR = Yes
    JSON_ATTR = text_line_data
    RECURSIVE = No
    EXPLODED -> AttributeRenamer
AttributeRenamer
    ATTR_LIST = text_line_data,_totalPages,
    -> AttributeKeeper_2
AttributeKeeper_2
    KEEP_ATTRS = _totalPages
    -> Tester_2
Tester_2
    TEST_CLAUSE = TEST @Value(_totalPages) <= 100
    BOOL_OP = OR
    TEST_MODE = Automatic
    TEST_DESCRIPTION = ""
    PASSED -> FeatureMerger_2 [input 2]
    FAILED -> Terminator
Terminator
    MESSAGE = There are more than 100 pages (100k results) for this indicator, processing failed!
Note: Attach the number of available pages to each page-requesting feature
FeatureMerger_2
    MERGE_TYPE = Attributes Only
    IGNORE_NULLS = No
    ATTR_CONFLICT_RES = Use Requestor
    SUPPLIERS_FIRST = No
    JOIN_KEYS = 1 1 AUTO
    PROCESS_DUPS = No
    ATTR_ACCUM_MODE = Merge Supplier
    MERGED -> Tester
Note: Keep only the queries that are for a page <= the number of available pages
Tester
    TEST_CLAUSE = TEST @Value(_Page) <= @Value(_totalPages)
    BOOL_OP = OR
    TEST_MODE = Automatic
    TEST_DESCRIPTION = ""
    PASSED -> AttributeCopier_2
AttributeCopier_2
    ATTR_LIST = _URLTemplate,_URL,
    -> StringReplacer_3
StringReplacer_3
    CASE = no
    REPLACE_TEXT = @Value(_IndicatorID)
    SRC_ATTRS = _URL
    REGEXP = no
    NO_MATCH = _FME_NO_OP_
    FIND_TEXT = {IndID}
    -> StringReplacer_4
StringReplacer_4
    CASE = no
    REPLACE_TEXT = @Value(_Page)
    SRC_ATTRS = _URL
    REGEXP = no
    NO_MATCH = _FME_NO_OP_
    FIND_TEXT = {PageNum}
    -> FeatureReader_2
    -> StringReplacer_4_Output
Note: Query page 2 - limit
FeatureReader_2
    FORMAT = TEXTLINE
    ATTR_CONFLICT_RES = Use Result
    FEATURETYPES_RADIO = FEATURETYPES
    OUTPUT_FEATURES_DISPLAY = Based on Connections
    TEXTLINE_READ_WHOLE_FILE_AT_ONCE = YES
    DATASET = @Value(_URL)
    ATTRS_TO_EXPOSE = text_line_data
    ATTR_ACCUM_MODE = Merge Initiator and Result
    COMBINE_GEOM = Use Result
    <OTHER> -> JSONFragmenter_2
Note: Get the data of this page
JSONFragmenter_2
    EXPLODE_FORMAT = JSON
    JSON_QUERY = json["Data"]
    PREF_STRING = DataList
    NEW_ATTRIBUTES = DataList{}
    EXTRACT_ATTR = Yes
    JSON_ATTR = text_line_data
    RECURSIVE = No
    EXPLODED -> ListExploder
    EXPLODED -> JSONFragmenter_2_Exploded
ListExploder
    ATTR_ACCUM_MODE = Merge Incoming List
    ATTR_CONFLICT_RES = Use Original
    LIST_ATTR = DataList{}
    INDEX_ATTR = _element_index
    LIST_FOUND -> AttributeExposer
AttributeExposer
    ATTR_LIST = ByVariableId,ByVariableLabel,CharacteristicCategory,CharacteristicLabel,CountryName,DataId,DHS_CountryCode,Indicator,IndicatorId,IsTotal,Precision,RegionId,SurveyId,SurveyType,SurveyYear,SurveyYearLabel,TableId,Value
    -> AttributeRemover
AttributeRemover
    REMOVE_ATTRS = DataList,json_index,json_type,text_line_data
    -> AttributeKeeper
AttributeKeeper
    KEEP_ATTRS = CountryName,DHS_CountryCode,Indicator,IndicatorId,RegionId,SurveyYear,Value,SurveyId,SurveyType
    -> FeatureMerger [input 1]
    -> AttributeKeeper_Output
    -> File1 (writer CSV_1)
File1 (writer CSV_1)
    attributes: CountryName auto, DHS_CountryCode auto, RegionId auto, SurveyId auto, SurveyType auto, SurveyYear auto, Indicator auto, IndicatorId auto, Value auto
AttributeKeeper_Output: Inspector
JSONFragmenter_2_Exploded: Inspector
StringReplacer_4_Output: Inspector
dhs_subnational_boundaries_all_avail_surveys (reader SHAPE_1)
    attributes: OBJECTID number(10,0), ISO char(2), FIPS char(2), DHSCC char(2), SVYTYPE char(3), SVYYEAR number(19,11), CNTRYNAMEE char(254), CNTRYNAMEF char(254), CNTRYNAMES char(254), DHSREGEN char(254), DHSREGFR char(254), DHSREGSP char(254), SVYID number(19,11), REG_ID char(15), Svy_Map char(3), MULTLEVEL char(3), LEVELRNK number(19,11), REGVAR char(254), REGCODE number(19,11), REGNAME char(254), OTHREGVAR char(254), OTHREGCO number(19,11), OTHREGNA char(254), LEVELCO char(254), LEVELNA char(254), REPALLIND char(254), REGNOTES char(254), SVYNOTES char(254), Shape_Leng number(19,11), Shape_Area number(19,11)
    -> FeatureMerger [input 2]
FeatureMerger
    MERGE_TYPE = Geometry
    SUPPLIERS_FIRST = No
    JOIN_KEYS = @Value(RegionId) @Value(REG_ID) AUTO
    PROCESS_DUPS = No
    MERGED -> FeatureMerger_Merged
    NOT_MERGED -> FeatureMerger_NotMerged
    MERGED -> NewFeatureType (writer OGCKML_1)
FeatureMerger_Merged: Inspector
FeatureMerger_NotMerged: Inspector
NewFeatureType (writer OGCKML_1)
    attributes: CountryName kml_char(200), DHS_CountryCode kml_char(200), RegionId kml_char(200), SurveyId kml_char(200), SurveyType kml_char(200), SurveyYear kml_char(200), Indicator kml_char(200), IndicatorId kml_char(200), Value kml_char(200)
