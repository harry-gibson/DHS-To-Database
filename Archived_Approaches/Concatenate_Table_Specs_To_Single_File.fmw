FME workspace Concatenate_Table_Specs_To_Single_File.fmw

Parameters:
- SourceDataset_CSV = \\129.67.26.176\map_data\DHS_Automation\DataExtraction\All\ParsedSpecs\*.FlatRecordSpec.csv   # Source CSV (CommaSeparatedValue) File(s)
- DestDataset_CSV = \\129.67.26.176\map_data\DHS_Automation\DataExtraction\All\ParsedSpecs_Concat   # Destination CSV (CommaSeparatedValue) Folder

Readers:
- CSV_1: CSV from $(SourceDataset_CSV)

Writers:
- CSV_2: CSV to $(DestDataset_CSV)

CSV (reader CSV_1)
    attributes: ItemType char(17), FileCode char(9), RecordName char(6), RecordTypeValue char(3), RecordLabel char(30), Name char(12), Label char(51), Start number(4,0), Len number(3,0), Occurrences number(3,0), ZeroFill char(3), DecimalChar char(3), Decimal char(1), FMETYPE char(13)
    -> AttributeExposer
AttributeExposer
    ATTR_LIST = fme_basename
    -> StringSearcher
StringSearcher
    STRING_TO_SEARCH = @Value(fme_basename)
    CASE = no
    REGEXP = ^\d+
    MATCHED_RESULT_ATTR = SurveyID
    MATCHED -> CSV (writer CSV_2)
CSV (writer CSV_2)
    attributes: ItemType char(17), SurveyIDDataColumnName char(9), SurveyID number(4,0), FileCode char(11), RecordName char(7), RecordTypeValue char(4), RecordLabel char(45), NameColumnName char(5), Name char(12), Label char(97), Start number(4,0), Len number(3,0), Occurrences number(3,0), ZeroFill char(4), DecimalChar char(3), Decimal char(1), FMETYPE char(13)
