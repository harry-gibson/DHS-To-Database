FME workspace translate_all_recordtypes_to_pg.fmw

Parameters:
- DestDataset_POSTGRES = postgres@localhost:5432/DHS_Surveys   # Connection
- SourceDataset_CSV = C:\Users\zool1301\Documents\DHS\Phase6\ExtractedSurveyRecords_Python\*.All.csv   # Source CSV (CommaSeparatedValue) File(s)
- FEATURE_TYPES =
- SourceDataset_CSV_3 = C:\Users\zool1301\Documents\DHS\Phase6\ExtractedSurveyRecords_Python\*.All.csv   # Source CSV (CommaSeparatedValue) File(s)

Readers:
- CSV_1: CSV from $(SourceDataset_CSV)
- CSV_2: CSV from $(SourceDataset_CSV_3)

Writers:
- POSTGRES_1: POSTGRES to $(DestDataset_POSTGRES)

REC01.All (reader CSV_1)
    attributes: FileCode char(7), CASEID char(18), V000 char(4), V001 number(4,0), V002 number(4,0), V003 number(3,0), V004 number(4,0), V005 number(8,0), V006 number(3,0), V007 number(5,0), V008 number(5,0), V009 number(3,0), V010 number(5,0), V011 number(5,0), V012 number(3,0), V013 number(2,0), V014 number(2,0), V015 number(2,0), V016 number(3,0), V017 number(5,0), V018 number(3,0), V019 number(3,0), V019A number(2,0), V020 number(2,0), V021 number(4,0), V022 number(3,0), V023 number(3,0), V024 number(2,0), V025 number(2,0), V026 number(2,0),
      V027 number(2,0), V028 number(4,0), V029 number(2,0), V030 number(3,0), V031 number(4,0), V032 number(2,0), V034 number(3,0), V040 number(4,0), V042 number(2,0), V044 char(1), G117B char(1), S903C number(2,0), V784X char(1), SH62B number(6,0), S326AB number(2,0), V763A number(2,0), S114E number(2,0), ML13F char(1), V504 number(2,0), SHH1 number(2,0), SH263 number(6,0), V851E char(1), V3A08R number(2,0), SG265B number(2,0), V851A char(1), M65L char(1), D118T number(2,0), D118XC char(1), D119K number(2,0), SG234 number(2,0),
      SG308 number(2,0), V784L char(1), B7 number(4,0), S539 number(2,0), V845 char(1), HV003 number(3,0), ML22A char(1), V704 number(3,0), SG292 number(6,0), SG302 number(2,0), M57M number(2,0), V767A char(1), SG116B number(3,0), MMC3 char(1), D103F char(1), V472E char(1), D105H number(2,0), SG228B number(2,0), SG283 number(6,0), V414J number(2,0), HV208 number(2,0), H11B number(2,0), SG265AF number(2,0), S577D number(3,0), SG269I number(2,0), V474G char(1), SLNWP number(2,0), SH6YX number(2,0), SHH1M number(3,0), SHH2 number(2,0),
      V471C char(1), HW53 number(4,0), V414Q char(1), SHH2D number(3,0), SH617 number(2,0), SH284 number(4,0), SH235AG number(6,0), SG216D number(2,0), SG242 number(2,0), D112N char(1), M42E number(2,0), SH6XY number(2,0), SH1X number(2,0), SH54 number(2,0), HC60 number(4,0), V481A char(1), V326 number(3,0), V802 number(5,0), CHL8 number(3,0), HV212 char(1), SG270I number(2,0), SINGRESOE number(7,0), SH246D number(6,0), HV001 number(4,0), SG215 number(2,0), SG265AZ number(2,0), H12I number(2,0), H32Q char(1), S523U number(2,0), SH_MIG char(15),
      H33Y number(5,0), V224 number(3,0), M42A char(1), S506A char(1), V218 number(3,0), SG201M number(2,0), S325J number(2,0), SG202D number(2,0), V161 number(3,0), SH244 number(6,0), V215 number(4,0), SHD4M number(3,0), V509 number(5,0), V510 number(2,0), S435GE number(2,0), SG220 number(2,0), M57C char(1), V414B char(1), SH284A number(4,0), HB5 number(5,0), S325M number(2,0), HML3 number(2,0), HC13 number(2,0), H40M char(1), SHT2M number(3,0), SHT3D number(3,0), V231 number(5,0), HW3 number(5,0), HC61 number(2,0), V768B char(1),
      SG228Y number(2,0), H6 number(2,0), S538P number(2,0), S540G number(2,0), SH4 number(2,0), ML13Y number(2,0), MM1 number(2,0), S540D number(2,0), HV246F char(1), S567 number(3,0), S577R number(3,0), S578I number(5,0), V474J char(1), HV105 number(3,0), HA52 number(2,0), SG201X number(2,0), SG257 number(3,0), SG304A number(2,0), SG284 number(2,0), S325FH number(2,0), V743A number(2,0), S435E number(2,0), HB2 number(5,0), V302 char(1), ML18C char(1), SG206A number(2,0), SH5 number(2,0), M2A number(2,0), M38 number(2,0), S433L number(3,0),
      V3A08O char(1), H32C number(2,0), V232 number(2,0), SH230 number(3,0), S937Z number(2,0), SH229 number(3,0), ML19F char(1), S540K number(2,0), S541B number(2,0), HV031 number(4,0), S325FD number(2,0), SG269D number(2,0), SG270D number(2,0), V843 char(1), S577K number(5,0), S578B number(9,0), SH222 number(2,0), H6Y number(5,0), V461 char(1), HV129 char(1), V3A08P number(2,0), S577P number(9,0), S578G number(3,0), V714 number(2,0), HV243D char(1), B1 number(3,0), S325D number(2,0), D118E number(2,0), HB13 number(2,0), SH110J number(2,0),
      HV121 number(2,0), M1C char(1), M8 number(3,0), ML14Z char(1), D115O number(2,0), D100A number(2,0), S541D number(2,0), M55Z number(2,0), M57H number(2,0), M2I number(2,0), M47 char(1), G117J char(1), SHMLC number(3,0), V414A char(1), SG228E number(2,0), SG115 number(2,0), HC33 number(2,0), SG222J number(2,0), SG223A number(2,0), M3G number(2,0), SG265AI number(2,0), IDXH4A number(3,0), SH9 number(2,0), V225 number(2,0), HC7 number(5,0), MM3 number(3,0), SH76U number(2,0), SG240E number(2,0), SG123H number(2,0), SG226 number(2,0),
      M2M number(2,0), M3D number(2,0), M52 number(3,0), S112A number(2,0), S541V number(2,0), SH19 number(2,0), SH20 number(2,0), SG251 number(6,0), D119XH char(1), SG305 number(3,0), HV247 number(2,0), HML12 number(2,0), S572C number(2,0), CHL4 number(3,0), SHMLD number(3,0), V538 char(1), S714BB number(2,0), S923 number(2,0), S325FZ number(2,0), SG201F number(2,0), HML32A char(1), SH68B number(3,0), SHCOLA number(2,0), V467E char(1), M57D char(1), V770P number(2,0), S573C number(3,0), V472Q char(1), V778 char(1), V478 char(1),
      V754CP number(2,0), SH231AG number(6,0), SH232 number(3,0), S540J number(2,0), M42C number(2,0), S541A number(2,0), SG216F number(2,0), SG304C number(2,0), V166 char(1), HB41 number(5,0), V744A number(2,0), V463B char(1), SH83 number(2,0), SG261 number(2,0), V770X number(2,0), SH292 number(2,0), SH110H number(2,0), S523P number(2,0), SH110G number(2,0), V762AJ char(1), V762BA char(1), S578V number(3,0), S581D number(2,0), IDXCH2 number(3,0), SG309 number(2,0), D103E char(1), HV041 number(3,0), SHRM4 number(6,0), SG241Y number(2,0), SG310 number(2,0),
      S435GB number(2,0), HV204 number(4,0), V121 number(2,0), S937F number(2,0), SG269Z number(2,0), AWFACTW number(5,0), SG270Z number(2,0), M6 number(3,0), SH2M number(3,0), V472S char(1), V474A char(1), SH3D number(3,0), S903D number(2,0), G103 number(2,0), HV253D char(1), SH197D number(2,0), HMHIDX2 number(3,0), HO101 number(2,0), ML16C char(1), SG253C number(4,0), H32D number(2,0), S523F number(2,0), SG241B number(2,0), HML32F char(1), S947 number(2,0), SH93 number(4,0), SG121 number(2,0), HSKIDX number(3,0), D120 number(3,0), V228 number(2,0),
      D123 char(1), HV115 char(1), SG112A number(7,0), M19A number(2,0), D119XE char(1), S951 number(3,0), SGRESULT number(3,0), S906A number(2,0), V233 number(2,0), V3A00L number(2,0), V537 number(3,0), HS102 number(2,0), D118XI char(1), HB12A number(6,0), G124 number(3,0), SH283T number(5,0), SH6YJ number(2,0), HV232B number(2,0), S523T number(2,0), HV243B char(1), D115H char(1), V784Q char(1), M49E char(1), CHL6 number(3,0), SH123D number(2,0), D118XD char(1), M2G number(2,0), M45 number(2,0), SG216H number(2,0), S577G1 number(3,0),
      D115R number(2,0), HV012 number(3,0), HB1 number(3,0), V104 char(1), SG228Z number(2,0), S938 number(2,0), SH227 number(6,0), HV017 number(2,0), S903Z number(2,0), S538O number(2,0), S540F number(2,0), HV235 number(2,0), SH202 number(3,0), V379 char(1), V380 char(1), S948 number(3,0), SG266B number(7,0), V413A char(1), HV027 number(2,0), V3A00Z number(2,0), V762AK char(1), V762BB char(1), H4M number(3,0), H5D number(3,0), V851B char(1), HW72 number(5,0), H37K number(2,0), S229C number(2,0), V844 char(1), HV019 number(2,0),
      HV020 number(2,0), SG126 number(7,0), SG228I number(2,0), V770I number(2,0), S906 number(2,0), S937C number(2,0), SH231AE number(6,0), D119XI char(1), S919 number(3,0), S920 number(2,0), H0M number(3,0), D118XH char(1), ML13G char(1), S578X number(9,0), S581F number(2,0), D118W number(2,0), D119N number(2,0), SG275 number(2,0), SH6YF number(2,0), M49X number(2,0), V212 number(3,0), HV226 number(3,0), HA57 number(2,0), SHHTEC number(4,0), SG123B number(2,0), V784K char(1), SG246X number(2,0), V474 char(1), H12H number(2,0), V412A number(2,0),
      M15 number(3,0), SGMUNIC char(1), SH216 number(3,0), ML13H number(2,0), ML15C char(1), V481C char(1), SH4Y number(5,0), SVALPRO number(6,0), V614 number(2,0), V3A08Z number(2,0), H37O number(2,0), S941 number(2,0), SG109 number(2,0), SG110 number(4,0), SG240I number(2,0), SH76 number(6,0), SG222Z number(2,0), S944 number(2,0), HC62 number(3,0), SH71U number(2,0), SGINTNUM number(4,0), HB55 number(2,0), S921 number(2,0), HB66 number(2,0), HA53 number(4,0), S540X number(2,0), S541O number(2,0), SHB2M number(3,0), V119 number(2,0), V120 number(2,0),
      SHB1Y number(5,0), SHB3D number(3,0), SG303B number(2,0), V158 number(2,0), S541M number(2,0), SH251AM number(3,0), V853C char(1), SG224 number(2,0), SG265D number(2,0), V316 number(5,0), SH68A number(2,0), SG246D number(2,0), HPCIDX number(3,0), S906B number(2,0), V204 number(2,0), SINGRTH number(9,0), SG232B number(6,0), M57U char(1), S937G number(2,0), D103B number(2,0), HV014 number(2,0), SREGALIAP number(7,0), H32L number(2,0), D117 char(1), M3K number(2,0), M60 number(2,0), HW18 number(3,0), S326 number(2,0), HC5 number(5,0), SHCOLC number(2,0),
      V375A char(1), V851K char(1), M65K char(1), V852B char(1), D101C number(2,0), ML19E char(1), HV228 char(1), HA11 number(5,0), V633G char(1), SG262A number(2,0), SG222B number(2,0), H2Y number(5,0), ML19Z char(1), V471D char(1), V465 char(1), SG258A number(2,0), V376 number(3,0), V471E char(1), V775 char(1), HMLIDX number(2,0), HS111 number(2,0), SH53 number(3,0), S540H number(2,0), SG246E number(2,0), S541S number(2,0), D110H char(1), HC73 number(5,0), SG229 number(3,0), S523I number(2,0), D110F char(1),
      S540L number(2,0), S541C number(2,0), V627 number(3,0), SH221 char(4), HV242 number(2,0), SH6XC number(2,0), S578K number(3,0), S579B number(5,0), SG223F number(2,0), HS108 number(2,0), SBONIFICA number(7,0), D118H char(1), HA12A number(6,0), SH80C number(3,0), H7Y number(5,0), ML13C number(2,0), SG127 number(3,0), ML0 number(2,0), V770C number(2,0), SGEDITO number(2,0), G113 char(1), V472A char(1), S945O number(2,0), V625A number(2,0), V762AI char(1), V762AR char(1), V307 number(2,0), V762BI char(1), D115XE char(1), S929 number(2,0),
      V322 number(2,0), S930 number(3,0), G117D char(1), HV238 number(3,0), SG247E number(2,0), V743F char(1), HV253A char(1), SHSMK char(1), SG279N number(2,0), S435GM number(2,0), SG123D number(2,0), H12C number(2,0), SHH2Y number(5,0), HB4 number(5,0), HA3 number(5,0), M65E char(1), S578P2 number(9,0), M71 number(4,0), B12 number(4,0), SH1H number(3,0), SH283Y number(5,0), D115XI char(1), SH28D number(3,0), SG265BB number(2,0), H12D number(2,0), V237 number(2,0), SG301A number(2,0), V855 char(1), S578Q number(3,0), HV227 char(1),
      SG123A number(2,0), V770J number(2,0), V219 number(3,0), V220 number(2,0), S572D number(2,0), SG252 number(2,0), V438 number(5,0), ML2 number(2,0), SHT1D number(3,0), V815C char(1), M57J number(2,0), S577E number(5,0), V616 number(4,0), H37J number(2,0), S903G number(2,0), SG204M number(3,0), D118A char(1), V820 char(1), SH235AA number(6,0), H12U number(2,0), MM12 char(1), S578W number(5,0), S581E number(2,0), SH235AF number(6,0), SG204A number(5,0), S541G number(2,0), HO104 number(2,0), V414I number(2,0), V367 number(2,0), SH133B number(2,0),
      HV113 char(1), V761C char(1), V774C number(2,0), D105K char(1), SH231 number(3,0), SG282B number(2,0), V762AX char(1), V762BO char(1), V238 number(2,0), S577J number(3,0), S578A number(5,0), D116 number(3,0), SH96C number(6,0), SG240A number(2,0), S229B number(2,0), SG216B number(2,0), SG216Z number(2,0), V3A00R char(1), S222 number(2,0), HV237B number(2,0), SH242C number(3,0), V3A08S number(2,0), S578M number(5,0), S579D number(3,0), SHPC1 number(5,0), H32E number(2,0), V131 char(1), M49B number(2,0), H15I number(2,0), S572 number(3,0),
      SG265Z number(2,0), ML13A number(2,0), G114 char(1), V603 number(4,0), S223B number(2,0), SG241D number(2,0), HV253Z char(1), SG123E number(2,0), V812 number(2,0), SG249A number(2,0), V412C char(1), G123 number(2,0), V321 number(2,0), HW58 char(1), HV253E char(1), SHSD1 number(5,0), SHRM1 number(6,0), HV237F number(2,0), SH9Y number(5,0), SH227AB number(6,0), V304 char(1), SG241C number(2,0), M57P number(2,0), V3A08AB char(1), HV008 number(5,0), H3M number(3,0), H4D number(3,0), SHB1M number(5,0), V604 number(2,0), SHB2D number(5,0),
      D124 char(1), ML13K number(2,0), ML14B char(1), SH614 number(2,0), D119XJ char(1), V3A08AD char(1), SQUINTIP number(2,0), V784I char(1), S937A number(2,0), V129 number(3,0), V130 number(2,0), D118M number(2,0), V472T char(1), M55E number(2,0), V474B char(1), H38 number(2,0), D119D number(2,0), HV030 number(3,0), SH25M number(3,0), V471B char(1), V629 number(3,0), SH80MI number(3,0), V838B char(1), S326AC number(2,0), MM10 char(1), SH295A number(9,0), V770R number(2,0), V3A08X number(2,0), V784V char(1), HV230A number(2,0),
      S523L number(2,0), D119V number(2,0), SH515 number(2,0), V203 number(2,0), V784A char(1), SH249 number(6,0), SH250 number(6,0), SH70 number(6,0), SH248 number(2,0), H31 number(2,0), SG217F number(2,0), V152 number(3,0), IDX95 number(2,0), SG280A number(2,0), SH295BH number(3,0), SH69 number(2,0), V841 char(1), D115I char(1), FDYSTO number(4,0), S939 number(2,0), H41B char(1), H15L char(1), H2D number(3,0), H42 number(2,0), V414T char(1), HV246C char(1), SH21 number(2,0), SG265X number(2,0), ML13J number(2,0), ML14A char(1),
      SG269E number(2,0), SG270E number(2,0), HW6 number(6,0), SGHORAF number(3,0), MM7 number(3,0), SHIDX9 number(2,0), HML14 number(2,0), B8 number(3,0), H8M number(3,0), H9D number(3,0), S435D number(2,0), SG216X number(2,0), H37F char(1), SH125A number(2,0), M1B char(1), M29 number(2,0), D119XD char(1), SH6YA number(2,0), V3A08Q number(2,0), V827 char(1), SG201E number(2,0), H9M number(3,0), HW12 number(6,0), S325CH number(2,0), S931 number(2,0), SG218 number(2,0), V477 char(1), V625 number(2,0), H15M char(1), M4 number(3,0),
      SH233 number(3,0), SH615 char(6), M13 number(3,0), V463F char(1), SG247Z number(2,0), SH79U number(2,0), SH80U number(2,0), SIFUENTE3 number(7,0), HV216 number(3,0), HB0 number(3,0), V103 char(1), S1001 number(2,0), SHT3 number(2,0), V825 char(1), D101B number(2,0), SG304E number(2,0), V847 char(1), SH268 number(2,0), H32G number(2,0), SG222X number(2,0), V714A number(2,0), SGRESP number(3,0), SHMTX number(2,0), S913 number(3,0), SH3M number(3,0), SH4D number(3,0), HV244 number(2,0), SH62 number(2,0), SHP222 number(2,0), V472D char(1),
      S911 number(2,0), V822 char(1), SG285 number(2,0), ML21C char(1), H2M number(3,0), H3D number(3,0), M1 number(2,0), SHH3M number(3,0), S943 number(2,0), HV246I number(3,0), SG217H number(2,0), H15G number(2,0), H9 number(2,0), HV102 number(2,0), V739 number(2,0), V740 char(1), HV009 number(3,0), S908 number(3,0), HV010 number(2,0), V839A char(1), V840A char(1), HML18 number(2,0), IDXML number(2,0), V235 number(2,0), ML13L number(2,0), M57I number(2,0), V762AS char(1), M49G char(1), V762BJ char(1), S572X number(2,0),
      HV219 number(2,0), HV220 number(3,0), SH197C number(2,0), SH110L number(2,0), SGHORAI number(3,0), HV253B char(1), SG265AX number(2,0), SG228G number(2,0), HV253 char(1), M55J number(2,0), D110E char(1), V3A05 char(1), D101G number(2,0), V823 number(2,0), SG304X number(2,0), V842 char(1), HML7 number(3,0), D110A number(2,0), V408 char(1), S937B number(2,0), HV140 number(2,0), D115Y number(2,0), V784U char(1), SHT1Y number(5,0), M10 number(2,0), V838C char(1), SH63 number(2,0), V409 number(2,0), V410 number(2,0), D118XG char(1),
      HV011 number(2,0), HA67 number(3,0), V467K char(1), V743B number(2,0), SHD4Y number(5,0), HVIDX number(3,0), SG217C number(2,0), SG271 number(2,0), HML1 char(1), S506AY number(5,0), V835B char(1), D115N number(2,0), S714E number(2,0), SH118A number(2,0), SH251BH number(3,0), D105F number(2,0), SG240H number(2,0), D129 char(1), SG240X number(2,0), S114GX number(3,0), V824 char(1), S573D number(3,0), V395 char(1), V405 number(2,0), V851C char(1), D121 number(2,0), S569B number(2,0), S570B number(2,0), SH251A number(9,0), V535 number(2,0),
      V216 number(2,0), HB11 number(5,0), V850A char(1), S325O number(2,0), D118I char(1), SGMINUTI number(3,0), S326AX number(2,0), D119S number(2,0), D122A number(2,0), S903F number(2,0), SG119B number(2,0), SHB3 number(2,0), SG120B number(2,0), SG272B number(7,0), SH26 number(3,0), V829 char(1), H14 number(2,0), H12P number(2,0), V830 char(1), H32I number(2,0), SH273 number(5,0), AWFACTU number(5,0), SG247C number(2,0), HMLC number(3,0), SH80M number(3,0), SINGRTHP number(9,0), HV237K char(1), M39A number(2,0), V633A char(1), S523B number(2,0),
      S928 number(2,0), SH118B number(2,0), HA50 char(1), V3A08AC char(1), S583B number(3,0), V536 number(2,0), S541R number(2,0), V762AN char(1), V762BE char(1), HV116 number(2,0), SG235 number(2,0), SH78A number(6,0), M55K number(2,0), HML32G char(1), V3A08B number(2,0), SH6YE number(2,0), SG222K number(2,0), M65D char(1), MMC4 char(1), S577O number(5,0), S578F number(9,0), HV236 char(1), SG223B number(2,0), SG304D number(2,0), SH80AI number(5,0), H8Y number(5,0), H12J number(2,0), S435GK number(2,0), SH284G number(4,0), SG254 number(3,0),
      G106 number(3,0), CHL7 number(2,0), B10 number(2,0), V217 char(1), V472N char(1), D118P number(2,0), V527 number(4,0), D119G number(2,0), V784B char(1), D101J char(1), V784C char(1), S578P number(3,0), S579G number(9,0), HA35 char(1), SG118A number(7,0), SHBM number(5,0), SG208B number(7,0), SH3 number(2,0), H12Z number(2,0), D125 char(1), V472U char(1), V474C char(1), SG311 number(3,0), S523S number(2,0), HC32 number(5,0), SG301F number(2,0), V376A char(1), HV013 number(3,0), HV237E number(2,0), SHDISTRICT number(3,0),
      V414F number(2,0), H4Y number(5,0), SG105 number(2,0), SG269K number(2,0), S578Y number(3,0), S581G number(2,0), HV209 number(2,0), D101H char(1), SHD4 number(2,0), HV210 number(2,0), SG270K number(2,0), SH1Y number(5,0), SH55 number(2,0), V472R char(1), BORD number(3,0), HB58 char(1), SH238 number(6,0), HD101 number(4,0), SG123C number(2,0), ML13P char(1), V631 char(1), S28DAYS number(2,0), S714D number(2,0), H37G char(1), D105C number(2,0), SH9M number(3,0), ML15B char(1), SG256A number(2,0), V762BU char(1), MM14 number(3,0),
      H37A number(2,0), S540E number(2,0), HV218 number(2,0), SH234C number(6,0), HC52 number(2,0), HB3 number(5,0), V624 number(3,0), S577L number(9,0), S578C number(3,0), V762AC char(1), MMC1 number(3,0), SG222C number(2,0), S114B number(2,0), SH2X number(2,0), SG223E number(2,0), H5Y number(5,0), G117H char(1), M27 number(2,0), SHT2Y number(5,0), M65X char(1), HC12 number(6,0), V472G char(1), V415 number(2,0), SH212D number(2,0), H43 number(2,0), S435H number(4,0), V719 number(2,0), V454 number(2,0), B2 number(5,0), S435GF number(2,0),
      ML24C char(1), V761B char(1), H3Y number(5,0), SINGRESOIB number(3,0), H12G number(2,0), HV118 number(2,0), ML13Z number(2,0), S1004 number(2,0), H7 number(2,0), SH6YB number(2,0), HW51 number(3,0), H32J number(2,0), SHB13 number(2,0), V3A08L number(2,0), V613 number(3,0), V414W char(1), ML19A char(1), ML20A number(2,0), SHA0 number(3,0), SHRM3 number(6,0), SHSD3 number(5,0), SG241Z number(2,0), V468 number(2,0), SG301E number(2,0), SH295BM number(3,0), V234 number(2,0), V836 char(1), G119 number(2,0), HB32 number(5,0), V3A01 char(1),
      S584B number(3,0), M55C number(2,0), MM11 char(1), HA33 number(2,0), S937X number(2,0), HC11 number(5,0), V412B char(1), HA6 number(6,0), SH127B number(5,0), HA41 number(5,0), H2 number(2,0), S907 number(2,0), S573E number(5,0), S576C number(5,0), V3A08G number(2,0), S581J number(2,0), D107 number(2,0), V472H char(1), V784S char(1), SG237A number(2,0), IDX5CS number(3,0), V528 number(3,0), V325A char(1), V832C char(1), V853B char(1), MM8 number(5,0), D110C number(2,0), SH226 number(3,0), SG123X number(2,0), V467M char(1),
      SG219A number(2,0), HO106 number(2,0), V732 number(2,0), HV253G char(1), SHH3Y number(5,0), B4 number(2,0), HV230B number(2,0), D118XK char(1), HB40 number(5,0), V763C number(2,0), V767C char(1), V419 number(2,0), V420 char(1), ML101 char(1), S326AA number(2,0), S940M number(3,0), HV246J char(1), SG240D number(2,0), HB63 number(2,0), S541X number(2,0), M70 number(2,0), G112 char(1), M36 char(1), D115K number(2,0), M42B char(1), SG225B number(7,0), V762AF char(1), V744D number(2,0), SH127A number(2,0), B5 number(2,0),
      S522D number(2,0), V467L char(1), V851F char(1), HW17 number(3,0), H20 number(2,0), SH80A number(5,0), SG278 number(2,0), M3M number(2,0), M62 number(2,0), S581I number(2,0), V157 number(2,0), S1113 number(2,0), S926 number(2,0), SG113D number(6,0), V359 number(3,0), V360 number(3,0), V834C char(1), HV000 char(4), SG233 number(2,0), H36A number(2,0), SG223Z number(2,0), SG304B number(2,0), SH139C number(3,0), HV246H number(3,0), HC8 number(5,0), V762AP char(1), V762BG char(1), D127 char(1), D105E number(2,0), V481F char(1),
      HA62 char(1), SG223G number(2,0), SH139B number(3,0), SH231AC number(6,0), H12S number(2,0), V469E number(2,0), V851D char(1), V815A char(1), SG207B number(2,0), V762AH char(1), V302A number(2,0), S578U number(3,0), H12Y number(2,0), S581C number(2,0), SG247X number(2,0), SG241G number(2,0), M55I number(2,0), V414P number(2,0), M57N number(2,0), M49Z number(2,0), SG202H number(2,0), V446 number(5,0), V3A00K number(2,0), S573A number(2,0), HV239 char(1), HV240 char(1), HB35 number(3,0), V413D char(1), V784O char(1), M57L number(2,0),
      H6M number(3,0), H7D number(3,0), V418 number(2,0), S506AD number(3,0), HV213 number(3,0), SH68C number(3,0), SH197E number(2,0), V211 number(5,0), V311 char(1), V784F char(1), V472K char(1), V473B char(1), S325CB number(2,0), HA5 number(5,0), SG219B number(7,0), SINGRESOO number(8,0), M55L char(1), S577G2 number(5,0), V848 char(1), SG211 number(2,0), ML23A number(2,0), V122 number(2,0), S940Y number(5,0), D101E number(2,0), HW52 number(2,0), SG243A number(2,0), HML31 number(2,0), ML13X number(2,0), V414H number(2,0), VCAL char(73),
      S540I number(2,0), V805 number(4,0), M2B number(2,0), M39 number(2,0), G117Y char(1), SH128 number(3,0), SH68 number(2,0), HMLD number(3,0), D119T number(2,0), D122B number(2,0), H15C number(2,0), V750 number(2,0), D118C number(2,0), V754JP number(2,0), S573 number(3,0), SGINTM number(3,0), SH2D number(3,0), SH1M number(3,0), H37M number(2,0), V849 char(1), SG269C number(2,0), V754BP char(1), SG270C number(2,0), M1D number(3,0), M57T number(2,0), SH251 number(2,0), SH6XA number(2,0), HB51 number(3,0), V846 char(1), SG269B number(2,0),
      SG270B number(2,0), SG228C number(2,0), D118XJ char(1), SH215 number(3,0), M57A number(2,0), SG223K number(2,0), V770D number(2,0), V134 number(2,0), G109 char(1), G110 char(1), SH3H number(3,0), SH56 number(3,0), SG258B number(7,0), S523R number(2,0), D118Y number(2,0), D119P number(2,0), S325FX number(2,0), HML32B char(1), SH74 number(6,0), SH3X number(2,0), SG269X number(2,0), SG270X number(2,0), H32T number(2,0), S510J number(2,0), SH128B number(5,0), V3A00F number(2,0), HA69 char(1), HA70 char(1), V853A char(1), SGSUPERV number(4,0),
      G111 char(1), D119XG char(1), H41A char(1), SH71 number(3,0), D119W number(2,0), SG241I number(2,0), V409A char(1), V410A char(1), MMC5 number(3,0), D115B number(2,0), SG201J number(2,0), SG202A number(2,0), SH69A number(2,0), V471F char(1), V437 number(5,0), H32F number(2,0), HV023 number(3,0), HV101 number(3,0), ML19D char(1), SH279 number(2,0), SH280 number(5,0), V242 number(5,0), D110D char(1), S523D number(2,0), S903H number(2,0), SG107 number(2,0), HV040 number(4,0), HML30 number(3,0), V414V number(2,0), S577Q number(3,0),
      S578H number(3,0), V463X char(1), V472C char(1), SG264 number(2,0), H37N number(2,0), S435F number(2,0), G117X char(1), SH6YI number(2,0), M55X number(2,0), M57F number(2,0), S924 number(3,0), V769 char(1), V770 number(2,0), V3A02 char(1), V3A00H number(2,0), V202 number(2,0), SG227 number(6,0), M2K number(2,0), M55M char(1), V141 number(2,0), M3B number(2,0), M50 number(2,0), V323A number(3,0), S572B number(2,0), SHP216 number(3,0), V414E number(2,0), SGMINUTF number(3,0), SH6M number(3,0), S439A number(3,0), SH7D number(3,0),
      V462 char(1), SH92 number(3,0), SH259 number(6,0), HA1 number(3,0), SH260 number(6,0), V837 char(1), V213 number(2,0), V458 char(1), ML22B char(1), SH235AC number(6,0), S435GG number(2,0), H37Z number(2,0), SG113A number(6,0), HV106 number(2,0), V701 number(2,0), V633B char(1), V439 number(5,0), V440 number(5,0), V602 number(2,0), SH7M number(3,0), SH8D number(3,0), D103D char(1), SG217E number(2,0), V634 char(1), SG240Z number(2,0), S903E number(2,0), HB53 number(4,0), V784D char(1), SH251BM number(3,0), HV232D number(2,0),
      SG222F number(2,0), HV237 number(2,0), V312 number(3,0), ML22C char(1), HA56 number(4,0), SG116A number(3,0), ML13D number(2,0), D118L number(2,0), D119C number(2,0), H36F char(1), HML17 number(2,0), SG201D number(2,0), MMIDX number(3,0), V774B number(2,0), D100D number(2,0), HML2 char(1), H31C number(2,0), V502 number(2,0), D105A number(2,0), SH1MO number(3,0), B11 number(4,0), V833B char(1), M49Y number(2,0), HC51 number(3,0), SGINT number(9,0), M55G number(2,0), H10 number(2,0), ML13M number(2,0), V803 number(3,0), SG240B number(2,0),
      SH67 number(3,0), M57R number(2,0), HC19 number(5,0), D115XJ char(1), ML16A number(2,0), SH77C number(6,0), SVIVIG2 number(2,0), SG262B number(6,0), SH75U number(2,0), V384A number(2,0), S936 number(2,0), SH268I number(4,0), HS107 number(2,0), V756 number(2,0), M73 number(3,0), S114C number(2,0), D115G number(2,0), M65H char(1), V413B char(1), SH235AD number(6,0), HML11 number(2,0), V754DP number(2,0), V768C char(1), HV109 number(2,0), HW10 number(5,0), HV110 char(1), S591 number(3,0), V745A char(1), G117C char(1), SHED3 number(2,0),
      V3A00P char(1), V337 number(3,0), V761 char(1), V784H char(1), SG116C number(3,0), V784J char(1), SG217I number(2,0), SH8 number(2,0), V762AE char(1), S568E number(2,0), HV246 number(2,0), SVIVIG1 number(2,0), SG208A number(2,0), HV237X number(2,0), SH79 number(3,0), SH80 number(4,0), V411A number(2,0), HO103 number(2,0), V839 char(1), V840 char(1), SG265AB number(2,0), M3H number(2,0), SG247Y number(2,0), V457 number(2,0), V472O char(1), SG279U number(2,0), SG282C number(2,0), V762AV char(1), V762BM char(1), SG111 number(3,0),
      HV122 number(2,0), HV225 number(2,0), HW70 number(5,0), HV127 char(1), SG288 number(2,0), SH78 number(2,0), M5 number(3,0), SH1 number(14,0), V153 number(2,0), V472L char(1), HB52 number(2,0), MM5 char(1), V814 number(2,0), H0D number(3,0), H22 number(2,0), S569D number(2,0), S435GL number(2,0), V159 number(2,0), V160 number(2,0), S570D number(2,0), S306A number(2,0), M2F number(2,0), M44 char(1), SHCMC number(4,0), IDX92 number(3,0), HV007 number(5,0), SG256B number(6,0), SH3Y number(5,0), SH75 number(2,0), V633E char(1),
      SH227AG number(6,0), ML13E number(2,0), V762AO char(1), M57V char(1), V762BF char(1), SH295AD number(3,0), V414C char(1), D118V number(2,0), D119M number(2,0), HML32D char(1), HA65 number(2,0), V102 number(2,0), SHT2 number(2,0), V762BZ char(1), SH258 number(3,0), SG217Y number(2,0), S114G number(2,0), H37L number(2,0), V762AQ char(1), V762BH char(1), SH271 number(5,0), V3A00N number(2,0), SH94 number(6,0), H32X number(2,0), S576A number(3,0), S823B number(2,0), D118X number(2,0), D119O number(2,0), SH122C number(5,2), HC17 number(3,0),
      SG280B number(7,0), V124 number(2,0), V482B char(1), D130A char(1), HV207 number(2,0), SH91 number(2,0), HV044 char(1), SG216A number(2,0), H37D number(2,0), V467G char(1), SH133C number(2,0), SG265H number(2,0), V414D char(1), V3A00J number(2,0), V731 number(2,0), S577C number(3,0), V3A08N number(2,0), S576H number(9,0), HW8 number(5,0), SG202G number(2,0), ML1 number(3,0), HB56 number(4,0), SG228D number(2,0), BIDX number(3,0), H12K number(2,0), H13B number(2,0), V762AW char(1), V762BN char(1), SH8Y number(5,0), SH227AE number(6,0),
      SG222I number(2,0), SG237B number(6,0), SG241E number(2,0), V763E char(1), V137 number(2,0), S325A number(2,0), SH516 char(6), S541Y number(2,0), V138 number(2,0), D119XA number(2,0), HV246G number(3,0), V128 number(3,0), S536K number(2,0), SG281 number(2,0), V476 char(1), V207 number(2,0), REC84_GROUP char(1), HML5 number(2,0), G121 number(2,0), G107 number(3,0), HC58 char(1), SH224I number(4,0), D115S number(2,0), D117A number(2,0), IDX99 number(2,0), HIDX number(2,0), IDX96 number(2,0), SG269F number(2,0), SG270F number(2,0), SG207 number(3,0),
      HMLB number(3,0), S325CX number(2,0), HV103 number(2,0), M49A number(2,0), H12L number(2,0), HV221 number(2,0), HV246A char(1), HV237C number(2,0), HV246E char(1), V784T char(1), V744B number(2,0), S5YEARS number(2,0), V3A08A char(1), S325CE number(2,0), S916 number(2,0), S570 number(3,0), HC53 number(4,0), CHL5 number(2,0), V447A number(3,0), V3A04 char(1), V414R char(1), S575 number(9,0), HMLA number(3,0), SINGRESOTP number(8,0), S541E number(2,0), V784E char(1), V3A08F number(2,0), S103A number(2,0), SG277 number(2,0), H32A number(2,0),
      SH73 number(6,0), SG301H number(2,0), SG202X number(2,0), V227 number(2,0), H32P number(2,0), V768A char(1), V481B char(1), HS104 number(2,0), SG245 number(2,0), V813 number(2,0), SH2MO number(3,0), S578P1 number(5,0), SG248 number(2,0), S616 number(3,0), SG104 number(2,0), SH505 number(4,0), M49C char(1), HML34 char(6), SH79N number(7,0), SH80N number(7,0), G101 number(2,0), SH6YC number(2,0), S927 number(2,0), B13 number(2,0), V762AM char(1), V762AA char(1), V541 char(1), V481D char(1), V762BD char(1), SHB1D number(3,0),
      HC3 number(5,0), SH255D number(4,0), SH257 number(3,0), FSYSTO number(4,0), S904 number(2,0), SG230M number(3,0), SG201I number(2,0), V832B char(1), SINGRESOIP number(2,0), HB60 number(2,0), HB68 number(2,0), S540W number(2,0), S541N number(2,0), V811 number(2,0), V406 number(2,0), SG214 number(2,0), HML16A number(3,0), S714BC number(2,0), G118 number(2,0), D118Q number(2,0), D119H char(1), D119X number(2,0), SG286 number(6,0), V474D char(1), M55O char(1), SG253B number(4,0), S541L number(2,0), V466 char(1), V784P char(1), H12R char(1),
      M3J number(2,0), SHP221 number(4,0), SG202N char(1), HML16 number(3,0), SH76N number(7,0), HV128 char(1), HW5 number(5,0), V414K number(2,0), V715 number(3,0), V770V number(2,0), SG123J number(2,0), MIDX number(2,0), S909 number(2,0), S910 number(2,0), SHT3M number(3,0), D130B char(1), V444A number(5,0), SG216E number(2,0), D103C char(1), H31E number(2,0), D115E number(2,0), S903X number(2,0), SH110K number(2,0), SH295BC char(6), S582 number(2,0), V3A00C number(2,0), S325FA number(2,0), S578J number(9,0), S579A number(3,0), SG117A number(7,0),
      S576J number(3,0), S577A number(5,0), SHADULT35 number(2,0), SH242B number(2,0), SH223 number(3,0), ML19X char(1), D114 number(2,0), SHMLB number(3,0), SHED1 number(2,0), V529 number(4,0), V530 number(2,0), V511 number(3,0), IDXCHL number(3,0), SG225A number(2,0), S918 number(2,0), SG239 number(2,0), SIFUENTE2 number(7,0), V770L number(2,0), V413C char(1), SH255S number(4,0), S523G number(2,0), V503 number(2,0), S325CG number(2,0), H15H number(2,0), SHUPAZILA number(3,0), V3A00Q char(1), V763G char(1), SGZONA number(2,0), SH61 number(3,0), D101D number(2,0),
      M57Q number(2,0), V774A number(2,0), V3A06 char(1), V481E char(1), H12V number(2,0), SG201A number(2,0), D115XF char(1), SG201B number(2,0), AWFACTT number(5,0), SHP4D number(3,0), H32U number(2,0), V834B char(1), S541Q number(2,0), SH2 number(2,0), M42D number(2,0), SG101 number(3,0), HC1 number(3,0), V826A char(1), H3 number(2,0), S541K number(2,0), SH6YG number(2,0), V463G char(1), V3A00D number(2,0), D118S number(2,0), D119J number(2,0), D121A number(2,0), S522C number(2,0), SH231AD number(6,0), AWFACTE2 number(6,0), S932 number(2,0),
      HV206 number(2,0), SH123A number(2,0), SH198C number(2,0), D005 number(8,0), D119XK char(1), SH6YD number(2,0), H7M number(3,0), V3A00S number(2,0), M57X number(2,0), H8D number(3,0), V741 number(2,0), M17 number(2,0), V779 char(1), V780 char(1), MM15 char(1), D105D number(2,0), SG125 number(2,0), SG282A number(2,0), SH28C number(2,0), V464 char(1), HS105 number(2,0), SIFUENTE1 number(8,0), MMC2 number(3,0), REC31_GROUP number(2,0), V414N number(2,0), V3A03 char(1), S572A number(2,0), SH234 number(2,0), SH7 number(2,0), HML15 char(1),
      V507 number(3,0), S566 number(2,0), SHMLA number(3,0), ML13O char(1), SH283 number(9,0), SG240C number(2,0), SG241A number(2,0), H15B number(2,0), S577G number(3,0), SG241F number(2,0), G117A char(1), G104 number(2,0), D110G char(1), H31D number(2,0), SH283D number(3,0), D108 number(2,0), SG265AC number(2,0), V762AB char(1), V3A00W number(2,0), D101I char(1), S604A number(3,0), S578N number(9,0), S579E number(3,0), HV245 number(4,0), SH251B number(5,0), V838A char(1), HV237Z number(2,0), S922 number(2,0), D115W number(2,0), H37E number(2,0),
      V482A char(1), H13 number(2,0), HA13 number(2,0), SH242A number(6,0), SH264D number(4,0), SG202M number(2,0), M55H number(2,0), V762AT char(1), V762BK char(1), G108 number(3,0), H0 number(2,0), V474E char(1), HV026 number(2,0), SHP218 number(3,0), SH228 number(2,0), SG217Z number(2,0), M55B number(2,0), SHB2Y number(5,0), D115L number(2,0), V481H char(1), V455 number(2,0), G115 char(1), G122 number(3,0), HV004 number(4,0), SG114A number(7,0), SH139D number(3,0), D118D number(2,0), V763F char(1), V190 number(2,0), D105I number(2,0),
      D118B number(2,0), S435GA number(2,0), S325CC number(2,0), SHB3M number(3,0), SH251AY number(5,0), M55N char(1), V744E number(2,0), S578S number(5,0), S581A number(3,0), S946 number(2,0), SG241H number(2,0), HA12 number(6,0), HB57 number(2,0), V3A00V number(2,0), HS101 number(2,0), S541I number(2,0), V372A number(2,0), V106 number(2,0), H0Y number(5,0), H45 char(1), HV202 char(1), M2D number(2,0), SHB1 number(3,0), V363 number(3,0), SH94A number(2,0), M2N number(2,0), M3E number(2,0), D118XB char(1), SG247B number(2,0), M49F char(1),
      SH253 number(5,0), HML32E char(1), D100B number(2,0), HO105 number(2,0), HV234A number(2,0), HA54 number(2,0), HV107 number(2,0), SG244 number(2,0), V3A08J number(2,0), V3A09A char(1), HV246D char(1), ML11 char(1), S577F number(9,0), SG265AD number(2,0), V474H char(1), IDXHML number(2,0), SG238 number(2,0), V208 number(2,0), S576F number(3,0), S435C number(2,0), HS103 number(2,0), HW13 number(2,0), S577N number(3,0), S578E number(5,0), SHH2M number(3,0), SHH3D number(3,0), HV018 number(4,0), V763D char(1), S578R number(3,0), HD100 number(3,0),
      AWFACTE number(5,0), V632 number(2,0), V412 char(1), S569A number(2,0), S570A number(2,0), S576E number(3,0), V467H char(1), S580 number(3,0), SH96A number(6,0), V472P char(1), HV032 number(2,0), SH221AH number(3,0), HV237I char(1), HA55 number(2,0), SH241 number(6,0), V3A08V number(2,0), ML14Y char(1), V3A00A number(2,0), D119XB char(1), V3A08D number(2,0), HA0 number(3,0), V243 number(2,0), D115J number(2,0), SH0Y number(5,0), SGWEIGHT number(9,0), SG263 number(2,0), SH104A number(2,0), CHL1 number(2,0), HW56 number(5,0), HV016 number(3,0),
      S937E number(2,0), H37H number(2,0), SG265AY number(2,0), SG291 number(3,0), SH28 number(3,0), ML16B char(1), V414U char(1), SG269H number(2,0), S541P number(2,0), SG270H number(2,0), D1310A number(2,0), HC68 number(5,0), SHB3Y number(5,0), SG265C number(2,0), SG287 number(2,0), SH227AD number(6,0), ML19C char(1), SGPROVIN number(3,0), ML20C char(1), SHT1M number(3,0), H5M number(3,0), H6D number(3,0), SHT2D number(3,0), HV253X char(1), H32Y number(2,0), M65G char(1), D115U char(1), V3A08E number(2,0), SG119A number(7,0), SG120A number(6,0),
      ML19Y char(1), SH231AF number(6,0), HW71 number(5,0), SG223Y number(2,0), HMHIDX number(3,0), S325CZ number(2,0), S540A number(2,0), S435J number(2,0), S934 number(2,0), SH231AB number(6,0), SG221 number(2,0), S229A number(2,0), S325CA number(2,0), SG202K number(2,0), V3A07 number(3,0), SGINTD number(3,0), IDX9A number(3,0), SG203B number(3,0), V469X number(2,0), V472F char(1), AWFACTR number(5,0), V702 number(3,0), HC10 number(5,0), V417 number(2,0), V834A char(1), S905Y number(5,0), H44C char(1), D119Q number(2,0), V474F char(1), HV006 number(3,0),
      SH2H number(3,0), V851I char(1), V626 number(3,0), SH231AA number(6,0), SG217B number(2,0), HA63 char(1), S589 number(3,0), S523J number(2,0), S569E number(2,0), D105M char(1), HV243C char(1), SCORE number(3,0), D115T number(2,0), B16 number(3,0), SG202F number(2,0), SG123F number(2,0), H12M number(2,0), S506AM number(3,0), D115XD char(1), SH235AB number(6,0), HV246B number(3,0), SHFLG number(2,0), D118N number(2,0), D119E number(2,0), HV270 number(2,0), S410J number(3,0), M57B number(2,0), SH90 number(2,0), V362 number(2,0), SH33 number(2,0),
      V3A08T number(2,0), M2H number(2,0), M46 number(4,0), V319 number(2,0), V705 char(1), V320 number(2,0), HW2 number(5,0), V826 char(1), S823A number(2,0), M3F number(2,0), M54 number(2,0), V301 char(1), M49D char(1), S714BA number(2,0), V762BS char(1), V717 char(1), V785 number(2,0), S588 number(2,0), SG117B number(2,0), M9 number(3,0), SH23 number(3,0), HB33 number(2,0), SH286 number(2,0), HO102 number(2,0), H34 number(2,0), SG223H number(2,0), V472I char(1), D115XA number(2,0), HML21 number(2,0), HW57 number(2,0),
      V770F number(2,0), M19 number(5,0), SG253 number(4,0), D115XB char(1), V721 char(1), V421 char(1), V318 number(2,0), D119U char(1), D122C number(2,0), SH239 number(6,0), SH240 number(2,0), MM6 number(3,0), V766A char(1), HML6 number(2,0), SG268 number(2,0), SH133A number(3,0), S573B number(9,0), D104 number(2,0), HA32 number(5,0), ML15A number(2,0), SH218 number(3,0), V467A char(1), ML23B char(1), HA60 char(1), S435GZ number(2,0), HV042 number(2,0), V828 char(1), MM2 number(2,0), V445 number(5,0), HV124 number(3,0),
      H36C number(2,0), HC27 number(2,0), HV237D number(2,0), V113 number(3,0), SHH3 number(2,0), SGHOGAR number(3,0), D115XH char(1), SG123I number(2,0), V123 number(2,0), SG128 number(2,0), HML8 number(2,0), SH57 number(2,0), V393 char(1), HMLE char(1), S714AA number(2,0), V136 number(3,0), S435GH number(2,0), S325B number(2,0), V532 number(2,0), S1002 number(2,0), SG213B number(7,0), SG307 number(2,0), V833A char(1), SH4M number(3,0), SH5D number(3,0), HHID char(7), SH72 number(6,0), MM4 number(5,0), SH24 number(2,0), SG265AG number(2,0),
      S523O number(2,0), SG201H number(2,0), SH62A number(2,0), V447 number(2,0), V475 char(1), S523A number(2,0), D118XE char(1), SH25 number(2,0), HC15 number(2,0), SG232A number(2,0), SH295 number(2,0), SH25Y number(5,0), ML13B number(2,0), SH227AC number(6,0), S942 number(3,0), SH616 number(2,0), M1A number(2,0), M28 number(2,0), HC0 number(3,0), V115 number(4,0), S523N number(2,0), D115M number(2,0), SH27 number(2,0), H21A number(2,0), V139 number(3,0), V140 number(2,0), HO107 number(2,0), H32V number(2,0), H33M number(3,0), H40D char(1),
      SH221B number(4,0), SG265AA number(2,0), V501 number(2,0), HS106 number(2,0), SG112B number(2,0), S523C number(2,0), HV237A number(2,0), B15 number(2,0), SG223X number(2,0), M1E number(5,0), HML32 number(2,0), S540B number(2,0), HA66 number(2,0), H32N number(2,0), S541J number(2,0), V471G char(1), SCHL145 number(2,0), V443 number(6,0), S223A number(2,0), S326B number(3,0), HC2 number(5,0), SG265G number(2,0), V801 number(5,0), AWFACTE3 number(6,0), SH72U number(2,0), HB65 number(2,0), V474I char(1), SH72N number(7,0), S541T number(2,0), D119R number(2,0),
      SH251AD number(3,0), SGEDITC number(4,0), SG116D number(3,0), V777 char(1), V411 number(2,0), SG223I number(2,0), ML21A char(1), SG270Y number(2,0), HV123 number(2,0), HV237G number(2,0), SH0 number(2,0), SG301B number(2,0), D128 char(1), H40Y char(1), H37Y number(2,0), S435I number(2,0), S577I number(3,0), SG202I number(2,0), S576I number(3,0), S945 number(2,0), SGASTOTI char(1), SG231 number(3,0), S902 number(2,0), SG246B number(2,0), S325CD number(2,0), D119XF char(1), SH276 number(2,0), V467B char(1), V831 char(1), SHP221AH number(3,0),
      HV217 number(2,0), D112A number(2,0), S569C number(2,0), S823 number(2,0), S570C number(2,0), HV025 number(2,0), SH220B char(4), S523E number(2,0), S905M number(3,0), SH77 number(2,0), H32R char(1), SH77A number(6,0), SG122 number(2,0), SG216I number(2,0), V414G number(2,0), HWIDX number(2,0), V762BR char(1), S933 number(2,0), D101A number(2,0), V463Z char(1), IDX98 number(2,0), V101 number(2,0), S576D number(9,0), V414L number(2,0), SHT1 number(2,0), H31B number(2,0), D115V number(2,0), HW15 number(2,0), V626A number(3,0), V394 char(1),
      V404 number(2,0), V384C number(2,0), HML35 number(2,0), SH251BC char(6), SHB2 number(3,0), V531 number(3,0), S577B number(9,0), V317 number(5,0), V471A char(1), HA40 number(5,0), M57G number(2,0), S325FE number(2,0), SH6YH number(2,0), H44A number(3,0), SH254 number(3,0), SG228X number(2,0), SG269A number(2,0), HV232 number(2,0), SG270A number(2,0), SG222D number(2,0), SG274 number(6,0), V416 char(1), SG303A number(2,0), SG113B number(6,0), V456 number(4,0), SG114B number(7,0), HO100 number(3,0), HML32C char(1), S587 number(3,0), S581X number(2,0),
      V815B char(1), M2J char(1), M3A number(2,0), M48 char(1), HW4 number(5,0), S1003 number(2,0), SHCOL21A number(3,0), HV126 char(1), HV253C char(1), V467D char(1), HV205 number(3,0), V444 number(6,0), SHP4Y number(5,0), HV246K char(1), HA68 number(2,0), SH286I number(4,0), SG222H number(2,0), SH295AM number(3,0), S803A number(2,0), V472B char(1), ML23C char(1), SG209 number(2,0), SG210 number(2,0), V835C char(1), SH5M number(3,0), SH6D number(3,0), SH227AA number(6,0), SH82 number(2,0), SH264S number(4,0), V762AU char(1),
      V762BL char(1), SH224 number(2,0), HV120 number(2,0), V525 number(3,0), SG222A number(2,0), H32S number(2,0), B0 number(2,0), SH139E number(3,0), V762BT char(1), SH63B number(2,0), V770K char(1), SG228J number(2,0), SG230A number(5,0), SH295B number(5,0), SG241X number(2,0), V3A00X number(2,0), V223 number(2,0), V767B char(1), V770U number(2,0), SHED2 number(3,0), SG223C number(2,0), V3A08I number(2,0), D115X number(2,0), SH77B number(6,0), V743C char(1), HML33 char(1), S114F number(2,0), S586 number(2,0), V513 number(2,0), V442 number(6,0),
      SH33D number(3,0), SH6XX number(2,0), HW11 number(5,0), SH13 number(2,0), V804 number(2,0), S578L number(3,0), S579C number(9,0), D115D number(2,0), H37P number(2,0), S523Q number(2,0), SG259 number(2,0), SG260 number(2,0), V441 number(6,0), SG265F number(2,0), HV232E char(1), SH212 number(4,0), V3A00B number(2,0), D115F number(2,0), G105 number(2,0), HV237J char(1), H32M number(2,0), H33D number(3,0), D100C number(2,0), HB69 number(8,0), HB70 number(4,0), SH128A number(2,0), HS100 number(2,0), SG202J number(2,0), SG203A number(2,0), M65F char(1),
      SH6Y number(5,0), MM9 number(3,0), V229 number(3,0), V230 number(5,0), D118O number(2,0), D119F number(2,0), D112 number(2,0), HC30 number(3,0), S519J number(2,0), HML4 number(3,0), HB12B number(6,0), V762AZ char(1), V762BQ char(1), V770M number(2,0), S912 number(2,0), V226 number(4,0), V481X char(1), H15F number(2,0), D118XA number(2,0), SH206 number(5,0), SINGRHI number(2,0), SG217A number(2,0), CHL2 number(3,0), SG289 number(7,0), V784M char(1), SG290 number(2,0), HA12B number(6,0), V835A char(1), HW1 number(3,0), SH7Y number(5,0),
      V3A00U number(2,0), M57E number(2,0), M57K number(2,0), B6 number(4,0), HDPIDX2 number(2,0), SH198D number(2,0), S914 number(2,0), M55F number(2,0), SH603 number(6,0), G117G char(1), HC9 number(6,0), SH6XZ number(2,0), S114A number(2,0), H12A number(2,0), SG269J number(2,0), SG270J number(2,0), V754WP number(2,0), M66 number(2,0), SHCOLB number(2,0), HML13 number(2,0), ML13I number(2,0), V806 number(2,0), V221 number(4,0), SG265I number(2,0), V770E number(2,0), S581H number(2,0), V3A00O number(2,0), H47 number(2,0), V851J char(1), V852A char(1),
      V821C char(1), S571 number(2,0), S584 number(3,0), V168 char(1), V133 number(3,0), V191 number(8,0), V201 number(3,0), V3A08U number(2,0), H46A number(3,0), V414O number(2,0), H11 number(2,0), V762AL char(1), V304A char(1), V762BC char(1), SG301X number(2,0), SH235 number(2,0), HV112 char(1), SH295AY number(5,0), V214 number(2,0), V729 number(2,0), V730 number(3,0), H12N number(2,0), V467F char(1), S578T number(9,0), S581B number(5,0), D119XC char(1), H32W number(2,0), V474Z char(1), HC64 number(3,0), SG265A number(2,0),
      SG265AE number(2,0), SG223J number(2,0), V426 number(4,0), HW73 number(5,0), S536A number(2,0), V327 number(2,0), V784G char(1), S325E number(2,0), D118K number(2,0), D119B number(2,0), S523X number(2,0), V361 number(2,0), SH2Y number(5,0), D118G number(2,0), SH618 char(6), SH205 number(5,0), SG201N number(2,0), SG202E number(2,0), SG223D number(2,0), HV271 number(8,0), V481G char(1), V222 number(4,0), SG222G number(2,0), SINGRESOIPA number(2,0), D115XK char(1), SH81 number(3,0), SH0D number(3,0), SH22 number(2,0), SG240G number(2,0), HC57 number(2,0),
      SG265E number(2,0), S523H number(2,0), V467J char(1), V770H number(2,0), V467I char(1), S325FC number(2,0), V459 char(1), V460 char(1), S945A number(2,0), HC4 number(5,0), H33 number(2,0), HW19 number(5,0), SG240F number(2,0), S541U number(2,0), H15J char(1), HDPIDX number(3,0), S229D number(3,0), V481 char(1), V633C char(1), H12Q char(1), V850B char(1), D126 char(1), V633D char(1), V762BP char(1), SH3MO number(3,0), V3A00M number(2,0), HA51 char(1), M3N number(2,0), M3I number(2,0), SG265AH number(2,0),
      H37B number(2,0), S903A number(2,0), V769A char(1), V770A number(2,0), HV243A number(2,0), V156 char(1), SHWH number(2,0), SG306 number(2,0), D103A number(2,0), HC63 number(4,0), V763B number(2,0), MM13 char(1), S325FB number(2,0), SG205 number(3,0), S574 number(3,0), M65B char(1), V716 number(3,0), D118XF char(1), HMLIDX2 number(2,0), SG255 number(3,0), SH123C number(2,0), ML18B char(1), SH619 number(2,0), SH246S number(6,0), D105N char(1), V167 char(1), S578O number(3,0), S579F number(5,0), D111 number(2,0), V743D number(2,0),
      SG267 number(2,0), SH8M number(3,0), SH9D number(3,0), V770O number(2,0), D1310B number(3,0), H1 number(2,0), H21 number(2,0), SH123B number(3,0), V746 char(1), SH217 number(5,0), SALLINCI number(2,0), V770S number(2,0), SIFUENTE4 number(6,0), V463E char(1), IDXH4 number(3,0), S435GC number(2,0), HML19 number(2,0), H44B char(1), S541H number(2,0), HML20 number(2,0), HV201 number(3,0), H32B number(2,0), SH71N number(7,0), HS109 number(2,0), HS110 number(2,0), V323 number(3,0), S435GN number(2,0), D106 number(2,0), S576B number(3,0), SH235A number(2,0),
      M65A char(1), V851L char(1), V852C char(1), V474X char(1), SHP4M number(3,0), HV104 number(2,0), SHP220B number(4,0), S540C number(2,0), ML19B char(1), ML20B char(1), HW9 number(6,0), SG269G number(2,0), V851H char(1), S568D number(2,0), V851G char(1), D105L char(1), H37X number(2,0), V781 char(1), SG270G number(2,0), HA2 number(5,0), M65C char(1), HV015 number(2,0), SH506 number(5,0), SG246Z number(2,0), SG206B number(6,0), M2E number(2,0), H12O number(2,0), M43 number(2,0), HV241 number(2,0), V751 number(2,0),
      S577H number(9,0), SG250 number(2,0), M65I char(1), S104A number(2,0), HV237H char(1), HC18 number(3,0), V305 char(1), SH242 number(2,0), SH227AF number(6,0), HML9 number(3,0), SG228H number(2,0), V463A char(1), V384B number(2,0), H46B char(1), SG123G number(2,0), SG249B number(7,0), HV232Y number(2,0), HV253F char(1), HB50 number(2,0), S937D number(2,0), V623 number(2,0), V452A char(1), V833C char(1), V452C number(2,0), HB61 number(2,0), V770W number(2,0), B9 number(2,0), V506 char(1), HV214 number(3,0), HA4 number(5,0),
      V762BV char(1), SG113C number(6,0), V3A08M number(2,0), SH0M number(3,0), SH1D number(3,0), SG108 number(3,0), HB12 number(6,0), S325CF number(2,0), S568A number(2,0), SG301G number(2,0), SH78O number(3,0), V479 char(1), V480 char(1), V3A00G number(2,0), HV111 char(1), S114D number(2,0), SGESTR char(1), SH110I number(2,0), IDXMCS number(3,0), H12W char(1), HML1A char(1), SH262 number(6,0), H32K number(2,0), S903B number(2,0), V3A00T char(1), SH6YZ number(2,0), SH136 number(2,0), V821B char(1), SG118B number(2,0), V155 number(2,0),
      HV215 number(3,0), D115XC char(1), SH225 number(3,0), HB62 char(6), HC70 number(5,0), S112B number(2,0), S435GI number(2,0), SG246C number(2,0), H39 number(2,0), H40 char(1), SH281 number(5,0), V854B char(1), V413 number(2,0), SG106 number(2,0), SHT3Y number(5,0), V372 number(2,0), HC72 number(5,0), V467C char(1), SG246A number(2,0), HV022 number(3,0), S1005 number(2,0), H4 number(2,0), V453 number(4,0), HC16 number(3,0), SHP4 number(2,0), D115C number(2,0), G117F char(1), S536C number(3,0), VCOL number(2,0), D118F number(2,0),
      D118U char(1), D119L number(2,0), SLNPM number(2,0), M55D number(2,0), HC56 number(4,0), D115Q number(2,0), D105G number(2,0), G100 number(2,0), SHP221AM number(3,0), M3L number(2,0), M61 number(4,0), SG301C number(2,0), SH33Y number(5,0), SHP221B number(4,0), ML13N char(1), SH242I number(4,0), V315 number(3,0), H37I number(2,0), V762AD char(1), H15A number(2,0), V770G number(2,0), V633F char(1), SHC0 number(3,0), V239 number(2,0), V240 number(3,0), V3A08AA char(1), HA61 char(1), HW55 number(2,0), V508 number(5,0), M72 number(3,0),
      V841A char(1), HV108 number(3,0), H32O number(2,0), SH96B number(6,0), SHRM5 number(6,0), SG217G number(2,0), SH243 number(3,0), SG273 number(2,0), ML17B char(1), S326C number(2,0), S435GX number(2,0), S583 number(3,0), S577M number(3,0), S578D number(3,0), D115XG char(1), HV035 number(2,0), SH221AM number(3,0), SGDIGIT number(3,0), S325FF number(2,0), HC6 number(6,0), HW16 number(3,0), SG222E number(2,0), V743E char(1), H32H number(2,0), S536B number(3,0), SG301D number(2,0), ML12 char(1), H35 char(1), H12F number(2,0), D110B number(2,0),
      M2L number(2,0), M3C number(2,0), M51 number(4,0), V472J char(1), V463C char(1), V473A char(1), H36B number(2,0), V414S number(2,0), V3A08C number(2,0), S325N number(2,0), S541F number(2,0), HA58 char(1), S523M number(2,0), SG201C number(2,0), SH220 number(4,0), ML17A number(2,0), SGINTA number(5,0), HV021 number(4,0), HV211 number(2,0), SH236 number(2,0), S949 number(2,0), S950 number(3,0), SG243B number(7,0), V105 char(1), SH5Y number(5,0), HW7 number(5,0), V762BW char(1), HV028 number(8,0), V463D char(1), SH95 number(6,0),
      HML10 number(2,0), M11 number(4,0), SHCOLD number(2,0), S435GD number(2,0), SG201K number(2,0), SG202B number(2,0), V621 number(2,0), H12X number(2,0), SH08 number(2,0), M65J char(1), HV125 char(1), V469F number(2,0), V766B char(1), V206 number(3,0), SG216C number(2,0), M7 number(3,0), V539 char(1), V540 char(1), V770N number(2,0), V762BX char(1), SG276 number(4,0), H15 number(2,0), M57O number(2,0), S572Y number(2,0), SG129 number(2,0), SHD4D number(3,0), SG272A number(2,0), H15K char(1), V3A00I number(2,0), V3A08K number(2,0),
      V3A09B char(1), CHL3 number(2,0), D105B number(2,0), SG266A number(2,0), HV234 char(1), S568B number(2,0), SG103 number(3,0), SH283M number(3,0), S541W number(2,0), SH6XB number(2,0), SG217D number(2,0), SH278 number(2,0), V770T number(2,0), H37C char(1), D119Y number(2,0), G117E char(1), M35 char(1), ML21B char(1), S570X number(2,0), V452B char(1), S568C number(2,0), SG247A number(2,0), G102 number(2,0), G117I char(1), SHRESI number(2,0), SG303C number(2,0), V407 char(1), V3A08W char(1), SG124 number(2,0), SH33M number(3,0),
      V205 number(2,0), HB67 number(3,0), SH6 number(2,0), SH139A number(3,0), M57S number(2,0), SH604 number(5,0), D118J number(2,0), D119A char(1), M34 number(4,0), V116 number(3,0), HV024 number(2,0), HV005 number(8,0), SG292A number(7,0), V310 char(1), HOVIDX number(3,0), SG213A number(2,0), V107 number(2,0), SH237 number(6,0), V744C number(2,0), SHRI number(5,0), SG228F number(2,0), M14 number(3,0), HC71 number(5,0), ML17C char(1), HC31 number(5,0), SH279A number(2,0), SH517 number(2,0), V770Q number(2,0), S536D number(3,0), H15D number(2,0),
      D118R number(2,0), V209 number(2,0), V210 number(2,0), D119I char(1), IDX94 number(2,0), V3A00Y number(2,0), S585 number(2,0), V783 char(1), HC55 number(2,0), SG228A number(2,0), V241 number(5,0), H8 number(2,0), S915 number(3,0), SH245 number(6,0), SGCONGL number(5,0), V505 char(1), H5 number(2,0), D101F number(2,0), SH75N number(7,0), H36D number(2,0), S523V number(2,0), V784R char(1), H32Z number(2,0), S576G number(5,0), D102 number(2,0), H9Y number(5,0), SG201G number(2,0), V745B char(1), H36E char(1), SG202L number(2,0),
      SH104B number(3,0), S435GJ number(2,0), V821A char(1), SG247D number(2,0), V151 number(2,0), SH235AE number(6,0), SH284B number(4,0), V512 number(3,0), SGVISITS number(2,0), SH18 number(2,0), HV002 number(4,0), HA64 char(1), SHMLIDX number(2,0), V3A00E number(2,0), M18 number(2,0), V125 char(1), V605 number(2,0), V3A08H number(2,0), D109 number(3,0), HB6 number(6,0), S523K number(2,0), M55A number(2,0), SH122A number(2,0), HV253H char(1), H12E number(2,0), SHH1Y number(5,0), V313 number(2,0), SHCOL3B number(3,0), SG216G number(2,0), HO108 number(2,0),
      ML18A number(2,0), H12T number(2,0), V364 number(2,0), V472M char(1), H15E number(2,0), HV252 number(2,0), SG253A number(4,0), S917 number(3,0), H12B number(2,0), V762AG char(1), D115P number(2,0), V482C char(1), V149 number(2,0), V150 number(3,0), V628 number(3,0), D113 number(2,0), SHH1D number(3,0), V135 number(2,0), SG201L number(2,0), SG202C number(2,0), V127 number(3,0), V401 number(2,0), V770B number(2,0), D105J char(1), V854A char(1), SG217X number(2,0), M2C number(2,0), HV232C number(2,0), SHP220 number(4,0), V784N char(1),
      GIDX number(2,0), HB64 number(2,0), HV117 number(2,0), SH197B number(3,0), S523W number(2,0), G116 char(1), V414M number(2,0), S937H number(2,0), B3 number(5,0), HV114 char(1)
    -> _All_
    -> BulkAttributeRenamer
_All_: Inspector
BulkAttributeRenamer
    PATTERN_ACTION_DISP = Change Case
    ATTRCHOICE = All Attributes
    CASE_CHANGE_TYPE = lowercase
    -> AttributeExposer
AttributeExposer
    ATTR_LIST = fme_feature_type
    -> AttributeCopier
AttributeCopier
    ATTR_LIST = fme_feature_type,tbname,
    -> StringReplacer
StringReplacer
    SRC_ATTRS = tbname
    REGEXP = no
    CASE = no
    FIND_TEXT = .
    REPLACE_TEXT = _
    NO_MATCH = _FME_NO_OP_
    -> Table1 (writer POSTGRES_1)
Table1 (writer POSTGRES_1) [off]
