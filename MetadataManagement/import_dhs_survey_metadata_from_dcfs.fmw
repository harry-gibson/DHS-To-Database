FME workspace import_dhs_survey_metadata_from_dcfs.fmw

Parameters:
- CSV_RecordSpec = C:\Users\zool1301\Documents\DHS\Phase5\SurveySpecs_Final\ALIR50.FlatRecordSpec.csv   # Optional: Pre-parsed CSV record spec file, or NA
- CSV_ValueSpec = C:\Users\zool1301\Documents\DHS\Phase5\SurveySpecs_Final\ALIR50.FlatValuesSpec.csv   # Optional: Pre-parsed CSV value spec file, or NA
- SurveyIDMapFile = C:\Users\zool1301\Documents\DHS\DHS_Info\SurveyIdsByFile_P5.csv   # CSV file containing mapping between different survey ID systems
- DestDataset_POSTGRES = staging_rw@map.zoo.ox.ac.uk:5434/staging   # Output DB connection
- dcf_file = C:\Users\zool1301\Documents\DHS\RecodeManuals\Recode6.dcf   # Optional: Run for a single DCF file, or NA
- SourceDataset_PATH = C:\Users\zool1301\Documents\DHS\Phase5\ExtractedSurveysAndShapes   # Optional: Run for all DCFs in this folder, or NA
- SourceDataset_POSTGRES = staging_rw@map.zoo.ox.ac.uk:5434/staging   # Connection
- CountrySpecific = True   # Is this DCF file country specific?

Readers:
- CSV_1: CSV from $(SurveyIDMapFile)
- CSV_2: CSV from $(CSV_RecordSpec)
- CSV_3: CSV from $(CSV_ValueSpec)
- PATH_1: PATH from $(SourceDataset_PATH)
- POSTGRES_1: POSTGRES from $(SourceDataset_POSTGRES)

Writers:
- POSTGRES_2: POSTGRES to $(DestDataset_POSTGRES)
- POSTGRES_3: POSTGRES to $(DestDataset_POSTGRES)

Note: Survey id mapping
CSV (reader CSV_1)
    attributes: SurveyFilename char(7), Country char(22), Year char(8), Survey_ID_num number(4,0), SurveyAPI_ID char(10), Type char(4)
    -> FeatureMerger [input 2]
FeatureReader
    WHERE = dhs_file_code = '@Value(dhs_file_code)'
    FEATURETYPES = dhs.dhs_surveys
    ATTRIBUTES = dhs.dhs_surveys,"dhs_file_code,dhs_numeric_id,dhs_api_id,record_type_start,record_type_len,country_specific"
    DATASET = staging_rw@map.zoo.ox.ac.uk:5434/staging
    POSTGRES_SCHEMALIST = dhs
    COMBINE_GEOM = Use Result
    FEATURETYPES_RADIO = FEATURETYPES
    ATTR_ACCUM_MODE = Only Use Result
    FORMAT = POSTGRES
    POSTGRES_QUERY_FEATURE_TYPES_FOR_MERGE_FILTERS = Yes
    POSTGRES_NAMED_CONNECTION = staging_rw@map.zoo.ox.ac.uk:5434/staging
    OUTPUT_FEATURES_DISPLAY = Based on Connections
    dhs.dhs_surveys -> Terminator_5
Terminator_5
    MESSAGE = This survey is already in the database! Translation Terminated!
Note: Attach the information that relates the different DHS identifier systems
FeatureMerger
    ATTR_ACCUM_MODE = Merge Supplier
    IGNORE_NULLS = No
    JOIN_KEYS = @Value(dhs_file_code) @Value(SurveyFilename) AUTO
    ATTR_CONFLICT_RES = Use Requestor
    SUPPLIERS_FIRST = No
    PROCESS_DUPS = No
    MERGE_TYPE = Attributes Only
    MERGED -> AttributeRenamer_2
    NOT_MERGED -> Terminator_4
AttributeRenamer_2
    ATTR_LIST = start,record_type_start,,len,record_type_len,,SurveyAPI_ID,dhs_api_id,,Survey_ID_num,dhs_numeric_id,
    -> dhs.dhs_surveys (writer POSTGRES_2)
    -> AttributeKeeper
Note: This table stores information that is necessary to being parsing a data file, specifically where in the line to look for the record type
Note: dhs_file_code provides the top level common link / TODO / - could add phase number, survey type, etc to this table or just create a view, as they are encapsulated in the file name / - country_specific likewise
dhs.dhs_surveys (writer POSTGRES_2)
    attributes: dhs_numeric_id int4, dhs_api_id varchar(10), record_type_start int4, record_type_len int4, dhs_file_code varchar(8),PRIKEY, country_specific bool
AttributeKeeper
    KEEP_ATTRS = dhs_file_code
    -> FeatureMerger_2 [input 2]
Terminator_4
    MESSAGE = Translation Terminated! Survey ID info not found in file for @Value(dhs_file_code)
Note: Process survey definition
Note: Process record type definition
Note: The first feature in the spec file for each record type (the rows are ordered by record type) defines the unique identifier for that record type (table)
Sampler_2
    RATE = 1
    GROUP_BY = record_code dhs_file_code
    SAMPLE_TYPE_LONG = First N Features
    SAMPLED -> AttributeRenamer_3
    NOT_SAMPLED -> FeatureMerger_3 [input 1]
AttributeRenamer_3
    ATTR_LIST = Name,id_var_name,,start,id_var_start,,len,id_var_len,,RecordTypeValue,record_type_val,,RecordLabel,record_desc,
    -> FeatureMerger_2 [input 1]
Note: Check we will not violate integrity, i.e. that the survey information is present
FeatureMerger_2
    ATTR_ACCUM_MODE = Merge Supplier
    IGNORE_NULLS = No
    JOIN_KEYS = @Value(dhs_file_code) @Value(dhs_file_code) AUTO
    ATTR_CONFLICT_RES = Use Requestor
    SUPPLIERS_FIRST = No
    PROCESS_DUPS = No
    MERGE_TYPE = Attributes Only
    MERGED -> SQLExecutor_3
    NOT_MERGED -> Terminator
Note: Add record id - we have to get this from the DB sequence thus making a query to the DB for every record we will be writing! / (It may be better to use the natural key of survey file and record name)
SQLExecutor_3
    POSTGRES_NAMED_CONNECTION = staging_rw@map.zoo.ox.ac.uk:5434/staging
    DATASET = staging_rw@map.zoo.ox.ac.uk:5434/staging
    POSTGRES_QUERY_FEATURE_TYPES_FOR_MERGE_FILTERS = Yes
    SQL_STATEMENT = select nextval('dhs.dhs_gen_id_seq'::regclass) as id
    COMBINE_ATTRS = Keep Initiator Attributes if Conflict
    FORMAT = POSTGRES
    EXPOSED_ATTRIBUTE_LIST = id
    COMBINE_GEOM = Initiator Geometry Only
    RESULT -> dhs.dhs_records (writer POSTGRES_2)
    RESULT -> AttributeKeeper_2
Note: dhs_file_code has FK to dhs_surveys so surveys must be loaded first - the feature merger will delay the features such that this is true
dhs.dhs_records (writer POSTGRES_2)
    attributes: record_code varchar(10), record_desc varchar(120), dhs_file_code varchar(80), record_type_val varchar(4), id_var_name varchar(30), id_var_start int4, id_var_len int4, id int4,PRIKEY
AttributeKeeper_2
    KEEP_ATTRS = dhs_file_code,id,record_code
    -> AttributeRenamer_4
AttributeRenamer_4
    ATTR_LIST = id,record_id,
    -> FeatureMerger_3 [input 2]
Note: Process recode (item) definition
Note: Get the id of the record to which this recode (item) belongs.
FeatureMerger_3
    ATTR_ACCUM_MODE = Merge Supplier
    IGNORE_NULLS = No
    JOIN_KEYS = @Value(dhs_file_code) @Value(dhs_file_code) AUTO @Value(record_code) @Value(record_code) AUTO
    ATTR_CONFLICT_RES = Use Requestor
    SUPPLIERS_FIRST = No
    PROCESS_DUPS = No
    MERGE_TYPE = Attributes Only
    NOT_MERGED -> Terminator_2
    MERGED -> AttributeRenamer_7
AttributeRenamer_7
    ATTR_LIST = Name,recode,
    -> FeatureMerger_7 [input 1]
Note: i'll be back
Terminator_2
    MESSAGE = Translation Terminated! No corresponding record info found for item @Value(Name) in file @Value(dhs_file_code)
Terminator
    MESSAGE = Translation Terminated! No corresponding survey info found for record @Value(record_code) in file @Value(dhs_file_code)
Note: We should only have one entry for each file/record/value combination and this is enforced in the DB. / But sometimes the data are a bit crap and so all we can do if we do find duplicates is discard the extras.
DuplicateRemover
    KEYATTR = FileCode Name Value
    DUPLICATE -> WARNING_Duplicate_Values_Discarded
    UNIQUE -> FeatureMerger_4 [input 1]
    UNIQUE -> StatisticsCalculator
Note: Group the values by recode and type (i.e. range, explicit coded value, or missing)
StatisticsCalculator
    COMPUTE_HISTOGRAM = NO
    COUNT_ATTR = _vals_count
    PREPEND_ATTR_NAME_CHOICE = For multiple results only
    GROUP_BY = FileCode Name ValueType
    STATS_ATTRS = Value
    SUMMARY -> Tester
Tester
    BOOL_OP = OR
    TEST_DESCRIPTION = ""
    TEST_CLAUSE = TEST @Value(_vals_count) > 0
    TEST_MODE = Automatic
    PASSED -> Tester_2
Note: Get the values which are related to ranges
Tester_2
    BOOL_OP = OR
    TEST_DESCRIPTION = ""
    TEST_CLAUSE:
      TEST @Value(ValueType) = RangeMin
      TEST @Value(ValueType) = RangeMax
      TEST @Value(ValueType) = ExpandedRange
    TEST_MODE = Automatic
    PASSED -> FeatureMerger_7 [input 2]
    FAILED -> Tester_3
Note: Is it a range-valued attribute?
FeatureMerger_7
    ATTR_ACCUM_MODE = Merge Supplier
    IGNORE_NULLS = No
    JOIN_KEYS = @Value(dhs_file_code) @Value(FileCode) AUTO @Value(recode) @Value(Name) AUTO
    ATTR_CONFLICT_RES = Use Requestor
    SUPPLIERS_FIRST = No
    PROCESS_DUPS = No
    MERGE_TYPE = Attributes Only
    MERGED -> AttributeCreator
    NOT_MERGED -> FeatureMerger_5 [input 1]
Note: Yes, set flag R (items with ranges and explicit values, other than missing, will be recorded as R)
AttributeCreator
    ATTR_LIST = recode_data_type,R
    -> SQLExecutor_2
Note: Get the values which are explicit from value lists
Note: There are some values for almost everything, as even Free Text ones have value(s) for missing or N/A. / We determine whether the values found mean this variable has a value list or is just free text + missing by saying if there are fewr than three values and the lowest of them is greater than 7 then it's probablly just defining missing values on a free-text field
Tester_3
    BOOL_OP = OR
    TEST_DESCRIPTION = ""
    TEST_CLAUSE = TEST @Value(ValueType) = ExplicitValue
    TEST_MODE = Automatic
    PASSED -> FeatureMerger_5 [input 2]
Note: Does it have any explicitly coded values (i.e. value lists)
FeatureMerger_5
    ATTR_ACCUM_MODE = Merge Supplier
    IGNORE_NULLS = No
    JOIN_KEYS = @Value(dhs_file_code) @Value(FileCode) AUTO @Value(recode) @Value(Name) AUTO
    ATTR_CONFLICT_RES = Use Requestor
    SUPPLIERS_FIRST = No
    PROCESS_DUPS = No
    MERGE_TYPE = Attributes Only
    MERGED -> AttributeCreator_2
    NOT_MERGED -> AttributeCreator_3
Note: Yes, set flag L
AttributeCreator_2
    ATTR_LIST = recode_data_type,L
    -> SQLExecutor_2
Note: No, set flag F
AttributeCreator_3
    ATTR_LIST = recode_data_type,F
    -> SQLExecutor_2
SQLExecutor_2
    POSTGRES_NAMED_CONNECTION = staging_rw@map.zoo.ox.ac.uk:5434/staging
    DATASET = staging_rw@map.zoo.ox.ac.uk:5434/staging
    POSTGRES_QUERY_FEATURE_TYPES_FOR_MERGE_FILTERS = Yes
    SQL_STATEMENT = select nextval('dhs.dhs_gen_id_seq'::regclass) as id
    COMBINE_ATTRS = Keep Initiator Attributes if Conflict
    FORMAT = POSTGRES
    EXPOSED_ATTRIBUTE_LIST = id
    COMBINE_GEOM = Initiator Geometry Only
    RESULT -> AttributeKeeper_3
    RESULT -> SubstringExtractor
SubstringExtractor
    END = 1
    SRC_STRING = @Value(dhs_file_code)
    RESULT_ATTR = country_code
    START = 0
    -> SubstringExtractor_2
SubstringExtractor_2
    END = 4
    SRC_STRING = @Value(dhs_file_code)
    RESULT_ATTR = phase_number
    START = 4
    -> SubstringExtractor_3
SubstringExtractor_3
    END = 99
    SRC_STRING = @Value(recode_description)
    RESULT_ATTR = recode_description
    START = 0
    -> dhs.dhs_recodes (writer POSTGRES_3)
Note: Alternative to using multiple writers would be to disable the FK constraints when starting the workbench and renable at the end. / Use these SQL statements to create the scrtipts that should then be run at start and end to do this (taken from http://stackoverflow.com/questions/139884/how-do-i-disable-referential-integrity-in-postgres-8-2): / Start: / SELECT 'ALTER TABLE '||nspname||'.'||relname||' DROP CONSTRAINT '||conname||';' / FROM pg_constraint / INNER JOIN pg_class ON conrelid=pg_class.oid / INNER JOIN pg_namespace ON pg_namespace.oid=pg_class.relnamespace / ORDER BY CASE WHEN contype='f' THEN 0 ELSE 1 END,contype,nspname,relname,conname / End: / SELECT 'ALTER TABLE '||nspname||'.'||relname||' ADD CONSTRAINT '||conname||' '|| pg_get_constraintdef(pg_constraint.oid)||';' / FROM pg_constraint / INNER JOIN pg_class ON conrelid=pg_class.oid / INNER JOIN pg_namespace ON pg_namespace.oid=pg_class.relnamespace / ORDER BY CASE WHEN contype='f' THEN 0 ELSE 1 END DESC,contype DESC,nspname DESC,relname DESC,conname DESC;
dhs.dhs_recodes (writer POSTGRES_3)
    attributes: id int4,PRIKEY, recode varchar(12),BTREE, recode_data_type varchar(2),BTREE, recode_description varchar(100), start int4, len int4, dhs_data_type char(2), occurrences int4, dhs_dec int4, is_sub_item bool, zero_fill bool, has_decimal_char bool, record_id int4,PRIKEY
AttributeKeeper_3
    KEEP_ATTRS = dhs_file_code,id,recode
    -> AttributeRenamer_5
AttributeRenamer_5
    ATTR_LIST = id,recode_id,
    -> FeatureMerger_4 [input 2]
Note: Get the id of the recode to which this value belongs
FeatureMerger_4
    ATTR_ACCUM_MODE = Merge Supplier
    IGNORE_NULLS = No
    JOIN_KEYS = @Value(FileCode) @Value(dhs_file_code) AUTO @Value(Name) @Value(recode) AUTO
    ATTR_CONFLICT_RES = Use Requestor
    SUPPLIERS_FIRST = No
    PROCESS_DUPS = No
    MERGE_TYPE = Attributes Only
    NOT_MERGED -> Terminator_3
    MERGED -> FeatureMerger_6 [input 1]
Note: I am unable to comply
Terminator_3
    MESSAGE = Translation Terminated! No corresponding recode info found for value @Value(Name) - @Value(Value) in file @Value(FileCode)
WARNING_Duplicate_Values_Discarded: Inspector
dhs.dhs_recode_value_types (reader POSTGRES_1)
    attributes: value_type int4,PRIKEY, value_type_desc varchar(50), value_type_short_desc varchar(15),PRIKEY
    -> FeatureMerger_6 [input 2]
Note: Get the type code corresponding to the value / type text (e.g. RangeMin -> 3)
FeatureMerger_6
    ATTR_ACCUM_MODE = Merge Supplier
    IGNORE_NULLS = No
    JOIN_KEYS = @Value(ValueType) @Value(value_type_short_desc) AUTO
    ATTR_CONFLICT_RES = Use Requestor
    SUPPLIERS_FIRST = Yes
    PROCESS_DUPS = No
    MERGE_TYPE = Attributes Only
    MERGED -> SQLExecutor
Note: Get an identifier from the database
SQLExecutor
    POSTGRES_NAMED_CONNECTION = staging_rw@map.zoo.ox.ac.uk:5434/staging
    DATASET = staging_rw@map.zoo.ox.ac.uk:5434/staging
    POSTGRES_QUERY_FEATURE_TYPES_FOR_MERGE_FILTERS = Yes
    SQL_STATEMENT = select nextval('dhs.dhs_gen_id_seq'::regclass) as id
    COMBINE_ATTRS = Keep Initiator Attributes if Conflict
    FORMAT = POSTGRES
    EXPOSED_ATTRIBUTE_LIST = id
    COMBINE_GEOM = Initiator Geometry Only
    RESULT -> AttributeRenamer_6
AttributeRenamer_6
    ATTR_LIST = Value,value_code,,ValueDesc,value_description,
    -> SubstringExtractor_4
SubstringExtractor_4
    END = 119
    SRC_STRING = @Value(value_description)
    RESULT_ATTR = value_description
    START = 0
    -> dhs_recode_values (writer POSTGRES_3)
dhs_recode_values (writer POSTGRES_3)
    attributes: id int4,PRIKEY, recode_id int4,BTREE, value_code varchar(10), value_description varchar(120), value_type int4
Note: Note! Joiner might be more efficient here but it doesn't seem to work with named connections. It says there was no password supplied... Bug!
Joiner [off]
    MATCH_RULE_DISPLAY = Must Match Exactly One (1:1)
    JOIN_KEYS = ValueType value_type_short_desc
    POSTGRES_QUERY_FEATURE_TYPES_FOR_MERGE_FILTERS = Yes
    CACHE_SIZE = 5000
    PREFETCH_EXHAUSTIVE = Yes
    DATASET = staging_rw@map.zoo.ox.ac.uk:5434/staging
    ADDED_FIELDS = value_type
    POSTGRES_NAMED_CONNECTION = staging_rw@map.zoo.ox.ac.uk:5434/staging
    FORMAT = POSTGRES
    TABLE = dhs.dhs_recode_value_types

Bookmark: Data input method 1: From files
Note: Record / item information - generated by python script which parses .DCF specificztion file into a flat CSV
CSV (reader CSV_2)
    attributes: FileCode char(7), RecordName char(7), RecordTypeValue char(4), RecordLabel char(50), Name char(12), Label char(77), Start number(4,0), Len number(3,0), Occurrences number(3,0), FMETYPE char(13), ZeroFill char(4), DecimalChar char(3), Decimal char(1)
    -> AttributeRenamer
Note: Values information
CSV (reader CSV_3)
    attributes: FileCode char(7), Name char(10), Value number(7,0), ValueDesc char(53), ValueType char(14)
    -> DuplicateRemover

Bookmark: Data input method 2: Read directory of DCF files
Note: Use this approach to just run all DCFs in a directory.
PATH (reader PATH_1) [off]
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> AttributeRenamer_8
AttributeRenamer_8
    ATTR_LIST = path_windows,dcfFN,
    -> AttributeKeeper_4

Bookmark: Data input method 3: Read DCF file from parameter
Note: Use this approach for best performance by running several copies of this WB at once from an external WB that has a path reader and runs several in parallel via WorkspaceRunner
Creator
    NUM = 1
    GEOMTYPE = Geometry Object
    CREATED -> ParameterFetcher
ParameterFetcher
    ATTR_LIST = dcfFN {$(dcf_file)}
    -> AttributeKeeper_4

Bookmark: Data input - run python parser
AttributeKeeper_4
    KEEP_ATTRS = dcfFN
    -> PythonCaller
    -> PythonCaller_2
Note: Parse DCF for recodes
PythonCaller
    PYTHONSOURCE:
      import fmeobjects
      from operator import itemgetter
      import re
      import os
      from difflib import SequenceMatcher as SM
      # DCF_Parser_Main.py should be in same dir as workbench file
      from DCF_Parser_Main import parseDCF
      class FeatureCreator(object):


          def input(self, feature):
              self.dcfFile = feature.getAttribute('dcfFN')
              parsedDCF = parseDCF(self.dcfFile)
              reqFieldNames = ['FileCode','RecordName','RecordTypeValue','RecordLabel','Name','Label','Start','Len','Occurrences',
                       'ZeroFill', 'DecimalChar', 'Decimal', 'FMETYPE']
              for item in parsedDCF:
                  feature = fmeobjects.FMEFeature()
                  for f in reqFieldNames:
                      if f in item:
                          feature.setAttribute(f,item[f])
                  feature.setAttribute("FMETYPE", "fme_char({0!s})".format(item['Len']))
                  self.pyoutput(feature)

          def __init__(self):
              pass
          def close(self):
              pass
    PYTHONSYMBOL = FeatureCreator
    NEW_ATTRIBUTES = FileCode RecordName RecordTypeValue RecordLabel Name Label Start Len Occurrences ZeroFill DecimalChar Decimal FMETYPE
    -> AttributeRenamer
Note: Parse DCF for values
PythonCaller_2
    PYTHONSOURCE:
      import fmeobjects
      from operator import itemgetter
      import re
      import os
      from difflib import SequenceMatcher as SM
      # DCF_Parser_Main.py should be in same dir as workbench file
      from DCF_Parser_Main import parseDCF

      class FeatureCreator(object):
          def input(self, feature):
              self.dcfFile = feature.getAttribute('dcfFN')
              parsedDCF = parseDCF(self.dcfFile)
              reqFieldNames = ['FileCode','RecordName','RecordTypeValue','RecordLabel','Name','Label','Start','Len','Occurrences',
                       'ZeroFill', 'DecimalChar', 'Decimal', 'FMETYPE']
              for item in parsedDCF:
                  if 'Values' in item and len(item['Values'])>0:
                      vals = item['Values']
                      for val in vals:
                          feature = fmeobjects.FMEFeature()
                          feature.setAttribute('FileCode',item['FileCode'])
                          feature.setAttribute('Name', item['Name'])
                          feature.setAttribute('Value', val[0])
                          feature.setAttribute('ValueDesc', val[1])
                          feature.setAttribute('ValueType', val[2])
                          self.pyoutput(feature)

          def __init__(self):
              pass
          def close(self):
              pass
    PYTHONSYMBOL = FeatureCreator
    NEW_ATTRIBUTES = FileCode Name Value ValueDesc ValueType
    -> DuplicateRemover

Bookmark: Data input
Note: Initial rename of attributes with common names in db
AttributeRenamer
    ATTR_LIST = FileCode,dhs_file_code,,Label,recode_description,,Len,len,,Start,start,,Occurrences,occurrences,,RecordName,record_code,,DecimalChar,has_decimal_char,,Decimal,dhs_dec,,ZeroFill,zero_fill,
    -> Sampler
Note: The first feature in the spec file defines how the record type can be read from all lines in the survey's data file
Sampler
    RATE = 1
    GROUP_BY = dhs_file_code
    SAMPLE_TYPE_LONG = First N Features
    SAMPLED -> FeatureMerger [input 1]
    NOT_SAMPLED -> Sampler_2
    SAMPLED -> FeatureReader
Note: Parse DCF for recodes
PythonCaller_3 [off]
    PYTHONSOURCE:
      import fmeobjects
      from operator import itemgetter
      import re
      import os
      from difflib import SequenceMatcher as SM

      class FeatureCreator(object):
          # We simply read the .DCF format file in line order, imputing the hierarchical structure from the order
      # of things, i.e. the level and record of an item is the previous found level or record
      # We also take advantage of the blank line between chunks as a line delimiter.

          def parseDCF(self, dcfFile):
              global parsedLines
              parsedLines = 0

              currentRecordName = 'N/A'
              currentRecordLabel = 'N/A'
              currentRecordType = 'N/A'
              currentLevelName = ''
              currentLevelLabel = ''

              currentValues = []
              skippingChunk = False

              currentlyParsing = "None"
              currentIdName = "None"
              currentIdLabel = "None"
              currentIdStart = 0
              currentIdLength = 0

              myRecords = {}
              myLevels = {}
              myItems = []
              myCountries = {}
              mySkippedChunks = []
              currentSurveyCode = os.path.basename(dcfFile).split(os.extsep)[0]
              chunkInfo = {
                  'FileCode':currentSurveyCode
              }

              #with open(r'C:\Users\zool1301\Documents\DHS\Namibia_Test\Hierarchical Format\NMIR60.DCF') as fileIn:
              with open(dcfFile) as fileIn:
              #with open(r'C:\Users\zool1301\Documents\DHS\RecodeManuals\MRecode6.dcf') as fileIn:

                  for line in fileIn:
                      parsedLines +=1
                      # Are we on a chunk start (a line with something in [Brackets])?
                      if line.find('[Level]') != -1:
                          currentChunkType = "Level"
                          skippingChunk = False
                          chunkInfo = {}
                      elif line.find('[Record]') != -1:
                          currentChunkType = "Record"
                          currentlyParsing = "Records"
                          skippingChunk = False
                          chunkInfo = {}
                      elif line.find('[Item]') != -1:
                          currentChunkType = "Item"
                          skippingChunk = False
                          chunkInfo = {}
                      elif line.find('[ValueSet]') != -1:
                          currentChunkType = "ValueSet"
                          skippingChunk = False
                          chunkInfo = {}
                      elif line.find('[IdItems]') != -1:
                          currentChunkType = "IdItems"
                          skippingChunk = False
                          currentlyParsing = "IdItems"
                          currentIdStart = 0
                          currentIdLength = 0
                          currentIdName = "None"
                          chunkInfo = {}
                      elif line.find('[Dictionary]') != -1:
                          currentChunkType = "Dictionary"
                          currentlyParsing = "Dictionary"
                          skippingChunk = False
                          recordTypeStart = 0
                          recordTypeLen = 0

                      elif line.find('[') != -1 and line.find(']') != -1:
                          # This is some chunk we don't know and/or care about.
                          skippingChunk = True
                          mySkippedChunks.append(line)

                      # Or are we on the end of a chunk, marked by a blank line?
                      elif line == '\n':
                          if skippingChunk:
                              # this was a bunch of lines we skip (e.g. those following '[Dictionary]')
                              skippingChunk = False
                          else:
                              # If we're at the end of a chunk defining a level or record then place the
                              # info into the globals so that the item parser will read them for items
                              # that FOLLOW afterward
                              if currentChunkType == 'Level':
                                  currentLevelName = chunkInfo['Name']
                                  currentLevelLabel = chunkInfo['Label']
                                  if myLevels.has_key(currentLevelName):
                                      if myLevels[currentLevelName] == currentLevelLabel:
                                          print "Warning, duplicate level name/label encountered at line "+str(parsedLines)
                                      else:
                                          raise ValueError("Duplicate level name encountered at line {0!s} with non-matched label".
                                                           format(parsedLines))
                                  myLevels[currentLevelName] = currentLevelLabel

                              elif currentChunkType == 'Record':
                                  # save into dirty globals so the subsequent items know what record they belong to
                                  currentRecordName = chunkInfo['Name']
                                  currentRecordLabel = chunkInfo['Label']
                                  currentRecordType = chunkInfo['RecordTypeValue']

                                  # save an "item" with the new record name/type/label reflecting the
                                  # id item for this record. In other words the first output row of each record
                                  # will describe the record itself and in particular the start/len of the id item
                                  chunkInfo['FileCode']=currentSurveyCode
                                  chunkInfo['Name'] = currentIdName
                                  chunkInfo['Label'] = currentIdLabel
                                  chunkInfo['Start'] = currentIdStart
                                  chunkInfo['Len'] = currentIdLength
                                  # apply the parent hierarchical labels, just stored in simple globals
                                  chunkInfo['RecordName'] = currentRecordName
                                  chunkInfo['RecordLabel'] = currentRecordLabel
                                  chunkInfo['RecordTypeValue'] = currentRecordType.strip("'")
                                  chunkInfo['LevelName'] = currentLevelName
                                  chunkInfo['LevelLabel'] = currentLevelLabel
                                  myItems.append(chunkInfo)

                                  if myRecords.has_key(currentRecordName):
                                      if myRecords[currentRecordName] == currentRecordLabel:
                                          print "Warning, duplicate record name/label encountered at line "+str(parsedLines)
                                      else:
                                          raise ValueError("Duplicate record name encountered at line {0!s} with non-matched label".
                                                           format(parsedLines))
                                  myRecords[currentRecordName] = currentRecordLabel

                              #elif currentChunkType == 'Dictionary'

                              # If we're at the end of a chunk defining a valueset then place the info
                              # into the last-processed item - valueset comes AFTER the item and a blank line,
                              # so the item will have already been added to the output list myItems
                              elif currentChunkType == 'ValueSet':
                                  # check it matches-ish. Either starts the same or text similarity is high
                                  # - sometimes they abbreviate the valueset but not the previous label
                                  s1 = chunkInfo['Label']
                                  s2 = myItems[-1]['Label']
                                  simRatio = SM(None,s1,s2).ratio()
                                  if not (simRatio > 0.7 or chunkInfo['Label'].find(myItems[-1]['Label']) == 0):
                                      print ("Warning, valueset did not seem to match item at line {0!s} of file {1!s} - please check!".
                                             format(parsedLines,dcfFile))
                                  if myItems[-1].has_key('Values'):
                                          # one item in the file (potentially more in others?) has two valueset chunks!
                                      myItems[-1]['Values'].extend(currentValues)
                                  else:
                                      myItems[-1]['Values'] = currentValues
                                  if chunkInfo.has_key('Range_Low_Value'):
                                      myItems[-1]['Range_Low_Value'] = chunkInfo['Range_Low_Value']
                                  if chunkInfo.has_key('Range_High_Value'):
                                      myItems[-1]['Range_High_Value'] = chunkInfo['Range_High_Value']
                                  if chunkInfo.has_key('Range_Desc'):
                                      myItems[-1]['Range_Desc'] = chunkInfo['Range_Desc']
                                  currentValues = []
                                  #else:
                                  #    raise ValueError("Error parsing valueset at line "+str(parsedLines))

                              elif currentChunkType == 'Dictionary':
                                  # This will be the first item in the file and will be written to the first
                                  # row of the output. It's an item that describes for all lines of the data file
                                  # where the record type can be found (start/len)
                                  chunkInfo['RecordName'] = '*'
                                  chunkInfo['RecordLabel'] = '*'
                                  chunkInfo['RecordTypeValue'] = '*'
                                  chunkInfo['Start'] = chunkInfo['RecordTypeStart']
                                  chunkInfo['Len'] = chunkInfo['RecordTypeLen']
                                  myItems.append(chunkInfo)

                              # Otherwise we are at the end of a chunk defining an actual item (recode)
                              elif currentChunkType == 'Item':
                                  if currentlyParsing == "Records":
                                      # apply the parent hierarchical labels, just stored in simple globals
                                      chunkInfo['RecordName'] = currentRecordName
                                      chunkInfo['RecordLabel'] = currentRecordLabel
                                      chunkInfo['RecordTypeValue'] = currentRecordType.strip("'")
                                      chunkInfo['LevelName'] = currentLevelName
                                      chunkInfo['LevelLabel'] = currentLevelLabel
                                      # "save" the information to the output list
                                      chunkInfo['FileCode']=currentSurveyCode
                                      myItems.append(chunkInfo)
                                  elif currentlyParsing == "IdItems":
                                      # this is a special case; it needs to be written out as an "item" for
                                      # each record. In the .dcf, IdItems comes after level info but before record
                                      # info. So save the info into dirty globals so that when we parse the record
                                      # info that follows we have access to it.
                                      currentIdName = chunkInfo['Name']
                                      currentIdLabel = chunkInfo['Label']
                                      currentIdStart = chunkInfo['Start']
                                      currentIdLength = chunkInfo['Len']
                      else:
                          # We are "within" a chunk of information
                          # add item key / value to the current chunk dictionary
                          # There are sometimes lines with more than one equals sign in (as it can appear in the
                          # description) so split at the FIRST = position only and clear up a bit (carriage return)
                          splitPos = line.find('=')
                          fieldName = line[0:splitPos].strip()
                          fieldVal = line[splitPos+1:].strip()
                          #fieldName,fieldVal = line.split('=')
                          if fieldName == 'Value':
                              # match value ranges based on pattern digits-colon-digits
                              if re.match('\d+:\d+', fieldVal):
                                  # use tuple unpacking to ensure that if we hit multiple : we will fail cleanly
                                  try:
                                      vMin, vMax = fieldVal.split(':')
                                      # the right hand side sometimes contains a description of the range values
                                      # after a semicolon
                                      if re.match('\d+;', vMax):
                                          vMax, valDesc = vMax.split(';')
                                      else:
                                          valDesc = ''
                                  except:
                                      valRange, otherCrap = fieldVal.split(';')
                                      vMin,vMax = valRange.split(':')
                                  #colonPos = fieldVal.find(':')

                                  chunkInfo['Range_Low_Value'] = vMin
                                  chunkInfo['Range_High_Value'] = vMax
                                  chunkInfo['Range_Desc'] = valDesc.strip()
                              # match "normal" value/description pairs based on digits-semicolon
                              elif re.match('\d+;', fieldVal):
                                  scPos = fieldVal.find(';')
                                  val = fieldVal[0:scPos]
                                  valDesc = fieldVal[scPos+1:]
                                  #val, valDesc = fieldVal.split(';')
                                  currentValues.append((val.strip(),valDesc.strip()))
                              # match horrible lines with VALUE given as string with quotes (see VCAL_VS1)
                              elif re.match('.+;', fieldVal):
                                  scPos = fieldVal.find(';')
                                  val = fieldVal[0:scPos]
                                  valDesc = fieldVal[scPos+1:]
                                  #val, valDesc = fieldVal.split(';')
                                  currentValues.append((val.strip("'").strip(),valDesc.strip("'").strip()))
                              # else save whatever we've got, presumably there is a value with no desc
                              else:
                                  currentValues.append((fieldVal,""))

                          elif not chunkInfo.has_key(fieldName):
                              # append the first occurrence of other labels. Subsequent ones will be silently discarded
                              chunkInfo[fieldName] = fieldVal
                  print "Parsed {0!s} lines into {1!s} items".format(parsedLines,len(myItems))
                  return myItems

          def input(self, feature):
              self.dcfFile = feature.getAttribute('dcfFN')
              parsedDCF = self.parseDCF(self.dcfFile)
              reqFieldNames = ['FileCode','RecordName','RecordTypeValue','RecordLabel','Name','Label','Start','Len','Occurrences',
                       'Range_Low_Value', 'Range_High_Value', 'Range_Desc', 'FMETYPE']
              for item in parsedDCF:
                  feature = fmeobjects.FMEFeature()
                  for f in reqFieldNames:
                      if f in item:
                          feature.setAttribute(f,item[f])
                  feature.setAttribute("FMETYPE", "fme_char({0!s})".format(item['Len']))
                  self.pyoutput(feature)

          def __init__(self):
              pass
          def close(self):
              pass
    PYTHONSYMBOL = FeatureCreator
    NEW_ATTRIBUTES = FileCode RecordName RecordTypeValue RecordLabel Name Label Start Len Occurrences ZeroFill DecimalChar Decimal FMETYPE
Note: Parse DCF for values
PythonCaller_4 [off]
    PYTHONSOURCE:
      import fmeobjects
      from operator import itemgetter
      import re
      import os
      from difflib import SequenceMatcher as SM

      class FeatureCreator(object):
          # We simply read the .DCF format file in line order, imputing the hierarchical structure from the order
      # of things, i.e. the level and record of an item is the previous found level or record
      # We also take advantage of the blank line between chunks as a line delimiter.

          def parseDCF(self, dcfFile):
              global parsedLines
              parsedLines = 0

              currentRecordName = 'N/A'
              currentRecordLabel = 'N/A'
              currentRecordType = 'N/A'
              currentLevelName = ''
              currentLevelLabel = ''

              currentValues = []
              skippingChunk = False

              currentlyParsing = "None"
              currentIdName = "None"
              currentIdLabel = "None"
              currentIdStart = 0
              currentIdLength = 0

              myRecords = {}
              myLevels = {}
              myItems = []
              myCountries = {}
              mySkippedChunks = []
              currentSurveyCode = os.path.basename(dcfFile).split(os.extsep)[0]
              chunkInfo = {
                  'FileCode':currentSurveyCode
              }

              #with open(r'C:\Users\zool1301\Documents\DHS\Namibia_Test\Hierarchical Format\NMIR60.DCF') as fileIn:
              with open(dcfFile) as fileIn:
              #with open(r'C:\Users\zool1301\Documents\DHS\RecodeManuals\MRecode6.dcf') as fileIn:

                  for line in fileIn:
                      parsedLines +=1
                      # Are we on a chunk start (a line with something in [Brackets])?
                      if line.find('[Level]') != -1:
                          currentChunkType = "Level"
                          skippingChunk = False
                          chunkInfo = {}
                      elif line.find('[Record]') != -1:
                          currentChunkType = "Record"
                          currentlyParsing = "Records"
                          skippingChunk = False
                          chunkInfo = {}
                      elif line.find('[Item]') != -1:
                          currentChunkType = "Item"
                          skippingChunk = False
                          chunkInfo = {}
                      elif line.find('[ValueSet]') != -1:
                          currentChunkType = "ValueSet"
                          skippingChunk = False
                          chunkInfo = {}
                      elif line.find('[IdItems]') != -1:
                          currentChunkType = "IdItems"
                          skippingChunk = False
                          currentlyParsing = "IdItems"
                          currentIdStart = 0
                          currentIdLength = 0
                          currentIdName = "None"
                          chunkInfo = {}
                      elif line.find('[Dictionary]') != -1:
                          currentChunkType = "Dictionary"
                          currentlyParsing = "Dictionary"
                          skippingChunk = False
                          recordTypeStart = 0
                          recordTypeLen = 0

                      elif line.find('[') != -1 and line.find(']') != -1:
                          # This is some chunk we don't know and/or care about.
                          skippingChunk = True
                          mySkippedChunks.append(line)

                      # Or are we on the end of a chunk, marked by a blank line?
                      elif line == '\n':
                          if skippingChunk:
                              # this was a bunch of lines we skip (e.g. those following '[Dictionary]')
                              skippingChunk = False
                          else:
                              # If we're at the end of a chunk defining a level or record then place the
                              # info into the globals so that the item parser will read them for items
                              # that FOLLOW afterward
                              if currentChunkType == 'Level':
                                  currentLevelName = chunkInfo['Name']
                                  currentLevelLabel = chunkInfo['Label']
                                  if myLevels.has_key(currentLevelName):
                                      if myLevels[currentLevelName] == currentLevelLabel:
                                          print "Warning, duplicate level name/label encountered at line "+str(parsedLines)
                                      else:
                                          raise ValueError("Duplicate level name encountered at line {0!s} with non-matched label".
                                                           format(parsedLines))
                                  myLevels[currentLevelName] = currentLevelLabel

                              elif currentChunkType == 'Record':
                                  # save into dirty globals so the subsequent items know what record they belong to
                                  currentRecordName = chunkInfo['Name']
                                  currentRecordLabel = chunkInfo['Label']
                                  currentRecordType = chunkInfo['RecordTypeValue']

                                  # save an "item" with the new record name/type/label reflecting the
                                  # id item for this record. In other words the first output row of each record
                                  # will describe the record itself and in particular the start/len of the id item
                                  chunkInfo['FileCode']=currentSurveyCode
                                  chunkInfo['Name'] = currentIdName
                                  chunkInfo['Label'] = currentIdLabel
                                  chunkInfo['Start'] = currentIdStart
                                  chunkInfo['Len'] = currentIdLength
                                  # apply the parent hierarchical labels, just stored in simple globals
                                  chunkInfo['RecordName'] = currentRecordName
                                  chunkInfo['RecordLabel'] = currentRecordLabel
                                  chunkInfo['RecordTypeValue'] = currentRecordType.strip("'")
                                  chunkInfo['LevelName'] = currentLevelName
                                  chunkInfo['LevelLabel'] = currentLevelLabel
                                  myItems.append(chunkInfo)

                                  if myRecords.has_key(currentRecordName):
                                      if myRecords[currentRecordName] == currentRecordLabel:
                                          print "Warning, duplicate record name/label encountered at line "+str(parsedLines)
                                      else:
                                          raise ValueError("Duplicate record name encountered at line {0!s} with non-matched label".
                                                           format(parsedLines))
                                  myRecords[currentRecordName] = currentRecordLabel

                              #elif currentChunkType == 'Dictionary'

                              # If we're at the end of a chunk defining a valueset then place the info
                              # into the last-processed item - valueset comes AFTER the item and a blank line,
                              # so the item will have already been added to the output list myItems
                              elif currentChunkType == 'ValueSet':
                                  # check it matches-ish. Either starts the same or text similarity is high
                                  # - sometimes they abbreviate the valueset but not the previous label
                                  s1 = chunkInfo['Label']
                                  s2 = myItems[-1]['Label']
                                  simRatio = SM(None,s1,s2).ratio()
                                  if not (simRatio > 0.7 or chunkInfo['Label'].find(myItems[-1]['Label']) == 0):
                                      print ("Warning, valueset did not seem to match item at line {0!s} of file {1!s} - please check!".
                                             format(parsedLines,dcfFile))
                                  if myItems[-1].has_key('Values'):
                                          # one item in the file (potentially more in others?) has two valueset chunks!
                                      myItems[-1]['Values'].extend(currentValues)
                                  else:
                                      myItems[-1]['Values'] = currentValues
                                  if chunkInfo.has_key('Range_Low_Value'):
                                      myItems[-1]['Range_Low_Value'] = chunkInfo['Range_Low_Value']
                                  if chunkInfo.has_key('Range_High_Value'):
                                      myItems[-1]['Range_High_Value'] = chunkInfo['Range_High_Value']
                                  if chunkInfo.has_key('Range_Desc'):
                                      myItems[-1]['Range_Desc'] = chunkInfo['Range_Desc']
                                  currentValues = []
                                  #else:
                                  #    raise ValueError("Error parsing valueset at line "+str(parsedLines))

                              elif currentChunkType == 'Dictionary':
                                  # This will be the first item in the file and will be written to the first
                                  # row of the output. It's an item that describes for all lines of the data file
                                  # where the record type can be found (start/len)
                                  chunkInfo['RecordName'] = '*'
                                  chunkInfo['RecordLabel'] = '*'
                                  chunkInfo['RecordTypeValue'] = '*'
                                  chunkInfo['Start'] = chunkInfo['RecordTypeStart']
                                  chunkInfo['Len'] = chunkInfo['RecordTypeLen']
                                  myItems.append(chunkInfo)

                              # Otherwise we are at the end of a chunk defining an actual item (recode)
                              elif currentChunkType == 'Item':
                                  if currentlyParsing == "Records":
                                      # apply the parent hierarchical labels, just stored in simple globals
                                      chunkInfo['RecordName'] = currentRecordName
                                      chunkInfo['RecordLabel'] = currentRecordLabel
                                      chunkInfo['RecordTypeValue'] = currentRecordType.strip("'")
                                      chunkInfo['LevelName'] = currentLevelName
                                      chunkInfo['LevelLabel'] = currentLevelLabel
                                      # "save" the information to the output list
                                      chunkInfo['FileCode']=currentSurveyCode
                                      myItems.append(chunkInfo)
                                  elif currentlyParsing == "IdItems":
                                      # this is a special case; it needs to be written out as an "item" for
                                      # each record. In the .dcf, IdItems comes after level info but before record
                                      # info. So save the info into dirty globals so that when we parse the record
                                      # info that follows we have access to it.
                                      currentIdName = chunkInfo['Name']
                                      currentIdLabel = chunkInfo['Label']
                                      currentIdStart = chunkInfo['Start']
                                      currentIdLength = chunkInfo['Len']
                      else:
                          # We are "within" a chunk of information
                          # add item key / value to the current chunk dictionary
                          # There are sometimes lines with more than one equals sign in (as it can appear in the
                          # description) so split at the FIRST = position only and clear up a bit (carriage return)
                          splitPos = line.find('=')
                          fieldName = line[0:splitPos].strip()
                          fieldVal = line[splitPos+1:].strip()
                          #fieldName,fieldVal = line.split('=')
                          if fieldName == 'Value':
                              # match value ranges based on pattern digits-colon-digits
                              if re.match('\d+:\d+', fieldVal):
                                  # use tuple unpacking to ensure that if we hit multiple : we will fail cleanly
                                  try:
                                      vMin, vMax = fieldVal.split(':')
                                      # the right hand side sometimes contains a description of the range values
                                      # after a semicolon
                                      if re.match('\d+;', vMax):
                                          vMax, valDesc = vMax.split(';')
                                      else:
                                          valDesc = ''
                                  except:
                                      valRange, otherCrap = fieldVal.split(';')
                                      vMin,vMax = valRange.split(':')
                                  #colonPos = fieldVal.find(':')

                                  chunkInfo['Range_Low_Value'] = vMin
                                  chunkInfo['Range_High_Value'] = vMax
                                  chunkInfo['Range_Desc'] = valDesc.strip()
                              # match "normal" value/description pairs based on digits-semicolon
                              elif re.match('\d+;', fieldVal):
                                  scPos = fieldVal.find(';')
                                  val = fieldVal[0:scPos]
                                  valDesc = fieldVal[scPos+1:]
                                  #val, valDesc = fieldVal.split(';')
                                  currentValues.append((val.strip(),valDesc.strip()))
                              # match horrible lines with VALUE given as string with quotes (see VCAL_VS1)
                              elif re.match('.+;', fieldVal):
                                  scPos = fieldVal.find(';')
                                  val = fieldVal[0:scPos]
                                  valDesc = fieldVal[scPos+1:]
                                  #val, valDesc = fieldVal.split(';')
                                  currentValues.append((val.strip("'").strip(),valDesc.strip("'").strip()))
                              # else save whatever we've got, presumably there is a value with no desc
                              else:
                                  currentValues.append((fieldVal,""))

                          elif not chunkInfo.has_key(fieldName):
                              # append the first occurrence of other labels. Subsequent ones will be silently discarded
                              chunkInfo[fieldName] = fieldVal
                  print "Parsed {0!s} lines into {1!s} items".format(parsedLines,len(myItems))
                  return myItems

          def input(self, feature):
              self.dcfFile = feature.getAttribute('dcfFN')
              parsedDCF = self.parseDCF(self.dcfFile)
              reqFieldNames = ['FileCode','RecordName','RecordTypeValue','RecordLabel','Name','Label','Start','Len','Occurrences',
                       'Range_Low_Value', 'Range_High_Value', 'Range_Desc', 'FMETYPE']
              for item in parsedDCF:
                  if 'Values' in item and len(item['Values'])>0:
                      vals = item['Values']
                      for val in vals:
                          feature = fmeobjects.FMEFeature()
                          feature.setAttribute('FileCode',item['FileCode'])
                          feature.setAttribute('Name', item['Name'])
                          feature.setAttribute('Value', val[0])
                          feature.setAttribute('ValueDesc', val[1])
                          self.pyoutput(feature)

          def __init__(self):
              pass
          def close(self):
              pass
    PYTHONSYMBOL = FeatureCreator
    NEW_ATTRIBUTES = FileCode Name Value ValueDesc ValueType
Note: Parse DCF for values (incl script embedded)
PythonCaller_5 [off]
    PYTHONSOURCE:
      import fmeobjects
      from operator import itemgetter
      import re
      import os
      from difflib import SequenceMatcher as SM

      class FeatureCreator(object):
          # We simply read the .DCF format file in line order, imputing the hierarchical structure from the order
      # of things, i.e. the level and record of an item is the previous found level or record
      # We also take advantage of the blank line between chunks as a line delimiter.

         # We simply read the .DCF format file in line order, imputing the hierarchical structure from the order
      # of things, i.e. the level and record of an item is the previous found level or record
      # We also take advantage of the blank line between chunks as a line delimiter.
          def parseDCF(self, dcfFile):
              global parsedLines
              parsedLines = 0

              # within-survey "globals" i.e. things we need to keep track of between items
              currentRecordName = 'N/A'
              currentRecordLabel = 'N/A'
              currentRecordType = 'N/A'
              currentLevelName = ''
              currentLevelLabel = ''
              currentSurveyDecChar = False
              currentSurveyZeroFill = False

              currentValues = []
              skippingChunk = False

              currentlyParsing = "None"
              currentIdName = "None"
              currentIdLabel = "None"
              currentIdStart = 0
              currentIdLength = 0

              myRecords = {}
              myLevels = {}
              myItems = []
              myCountries = {}
              mySkippedChunks = []
              currentSurveyCode = os.path.basename(dcfFile).split(os.extsep)[0]
              chunkInfo = {
                  'FileCode':currentSurveyCode
              }

              #with open(r'C:\Users\zool1301\Documents\DHS\Namibia_Test\Hierarchical Format\NMIR60.DCF') as fileIn:
              with open(dcfFile) as fileIn:
              #with open(r'C:\Users\zool1301\Documents\DHS\RecodeManuals\MRecode6.dcf') as fileIn:

                  for line in fileIn:
                      parsedLines +=1
                      # Are we on a chunk start (a line with something in [Brackets])?
                      if line.find('[Level]') != -1:
                          currentChunkType = "Level"
                          skippingChunk = False
                          chunkInfo = {}
                      elif line.find('[Record]') != -1:
                          currentChunkType = "Record"
                          currentlyParsing = "Records"
                          skippingChunk = False
                          chunkInfo = {}
                      elif line.find('[Item]') != -1:
                          currentChunkType = "Item"
                          skippingChunk = False
                          chunkInfo = {}
                      elif line.find('[ValueSet]') != -1:
                          currentChunkType = "ValueSet"
                          skippingChunk = False
                          chunkInfo = {}
                      elif line.find('[IdItems]') != -1:
                          currentChunkType = "IdItems"
                          skippingChunk = False
                          currentlyParsing = "IdItems"
                          currentIdStart = 0
                          currentIdLength = 0
                          currentIdName = "None"
                          chunkInfo = {}
                      elif line.find('[Dictionary]') != -1:
                          currentChunkType = "Dictionary"
                          currentlyParsing = "Dictionary"
                          skippingChunk = False
                          recordTypeStart = 0
                          recordTypeLen = 0

                      elif line.find('[') != -1 and line.find(']') != -1:
                          # This is some chunk we don't know and/or care about.
                          skippingChunk = True
                          mySkippedChunks.append(line)

                      # Or are we on the end of a chunk, marked by a blank line?
                      elif line == '\n':
                          if skippingChunk:
                              # this was a bunch of lines we skip (e.g. those following '[Dictionary]')
                              skippingChunk = False
                          else:

                              if currentChunkType == 'Dictionary':
                                  # This will be the first item in the file and will be written to the first
                                  # row of the output. It's an item that describes for all lines of the data file
                                  # where the record type can be found (start/len). It's a fudge to make this fit
                                  # the overall row format which is designed to describe an item
                                  chunkInfo['RecordName'] = '*'
                                  chunkInfo['RecordLabel'] = '*'
                                  chunkInfo['RecordTypeValue'] = '*'
                                  # the record type positioning is labelled in the DCF as "RecordTypeStart"(Len)
                                  # but we want to record it into the standard Start/Len columns of the output CSV
                                  # so just copy it over
                                  chunkInfo['Start'] = chunkInfo['RecordTypeStart']
                                  chunkInfo['Len'] = chunkInfo['RecordTypeLen']
                                  myItems.append(chunkInfo)
                                  # set the default values for the item parsing info
                                  currentSurveyZeroFill = chunkInfo['ZeroFill']
                                  currentSurveyDecChar = chunkInfo['DecimalChar']

                              # If we're at the end of a chunk defining a level or record then place the
                              # info into the globals so that the item parser will read them for items 7
                              # that FOLLOW afterward
                              elif currentChunkType == 'Level':
                                  currentLevelName = chunkInfo['Name']
                                  currentLevelLabel = chunkInfo['Label']
                                  if myLevels.has_key(currentLevelName):
                                      if myLevels[currentLevelName] == currentLevelLabel:
                                          print "Warning, duplicate level name/label encountered at line "+str(parsedLines)
                                      else:
                                          raise ValueError("Duplicate level name encountered at line {0!s} with non-matched label".
                                                           format(parsedLines))
                                  myLevels[currentLevelName] = currentLevelLabel

                              elif currentChunkType == 'Record':
                                  # save into dirty globals so the subsequent items know what record they belong to
                                  currentRecordName = chunkInfo['Name']
                                  currentRecordLabel = chunkInfo['Label']
                                  currentRecordType = chunkInfo['RecordTypeValue']

                                  # save an "item" with the new record name/type/label reflecting the
                                  # id item for this record. In other words the first output row of each record
                                  # will describe the record itself and in particular the start/len of the id item
                                  chunkInfo['FileCode']=currentSurveyCode
                                  chunkInfo['Name'] = currentIdName
                                  chunkInfo['Label'] = currentIdLabel
                                  chunkInfo['Start'] = currentIdStart
                                  chunkInfo['Len'] = currentIdLength
                                  # apply the parent hierarchical labels, just stored in simple globals
                                  chunkInfo['RecordName'] = currentRecordName
                                  chunkInfo['RecordLabel'] = currentRecordLabel
                                  chunkInfo['RecordTypeValue'] = currentRecordType.strip("'")
                                  chunkInfo['LevelName'] = currentLevelName
                                  chunkInfo['LevelLabel'] = currentLevelLabel
                                  myItems.append(chunkInfo)

                                  if myRecords.has_key(currentRecordName):
                                      if myRecords[currentRecordName] == currentRecordLabel:
                                          print "Warning, duplicate record name/label encountered at line "+str(parsedLines)
                                      else:
                                          raise ValueError("Duplicate record name encountered at line {0!s} with non-matched label".
                                                           format(parsedLines))
                                  myRecords[currentRecordName] = currentRecordLabel

                              #elif currentChunkType == 'Dictionary'

                              # If we're at the end of a chunk defining a valueset then place the info
                              # into the last-processed item - valueset comes AFTER the item and a blank line,
                              # so the item will have already been added to the output list myItems
                              elif currentChunkType == 'ValueSet':
                                  # check it matches-ish. Either starts the same or text similarity is high
                                  # - sometimes they abbreviate the valueset but not the previous label
                                  s1 = chunkInfo['Label']
                                  s2 = myItems[-1]['Label']
                                  simRatio = SM(None,s1,s2).ratio()
                                  if not (simRatio > 0.7 or chunkInfo['Label'].find(myItems[-1]['Label']) == 0):
                                      print ("Warning, valueset did not seem to match item at line {0!s} of file {1!s} - please check!".
                                             format(parsedLines,dcfFile))

                                  if 'ValueRanges' in chunkInfo:
                                      # If there was more than one range then expand each out to the individual values
                                      # This occurs with something like 1:12=age in months, 13:112 = (age in years +12)
                                      if len(chunkInfo['ValueRanges']) > 1:
                                          for rangeInfo in chunkInfo['ValueRanges']:
                                              thisRangeMin = int(rangeInfo[0])
                                              thisRangeMax = int(rangeInfo[1])
                                              thisRangeDesc = rangeInfo[2]
                                              assert thisRangeMax > thisRangeMin
                                              for expandedVal in range(thisRangeMin, thisRangeMax+1):
                                                  currentValues.append((expandedVal, thisRangeDesc, "ExpandedRange"))
                                      else:
                                          rangeInfo = chunkInfo['ValueRanges'][0]
                                          currentValues.append((rangeInfo[0],rangeInfo[2],"RangeMin"))
                                          currentValues.append((rangeInfo[1],rangeInfo[2],"RangeMax"))
                                          #myItems[-1]['Range_Low_Value'] = rangeInfo[0]
                                          #myItems[-1]['Range_High_Value'] = rangeInfo[1]
                                          #myItems[-1]['Range_Desc'] = rangeInfo[2]

                                  if myItems[-1].has_key('Values'):
                                          # one item in the file (potentially more in others?) has two valueset chunks!
                                      myItems[-1]['Values'].extend(currentValues)
                                  else:
                                      myItems[-1]['Values'] = currentValues
                                  #if chunkInfo.has_key('Range_Low_Value'):
                                  #    myItems[-1]['Range_Low_Value'] = chunkInfo['Range_Low_Value']
                                  #if chunkInfo.has_key('Range_High_Value'):
                                  #    myItems[-1]['Range_High_Value'] = chunkInfo['Range_High_Value']
                                  #if chunkInfo.has_key('Range_Desc'):
                                  #    myItems[-1]['Range_Desc'] = chunkInfo['Range_Desc']
                                  currentValues = []
                                  #else:
                                  #    raise ValueError("Error parsing valueset at line "+str(parsedLines))


                              # Otherwise we are at the end of a chunk defining an actual item (recode)
                              elif currentChunkType == 'Item':
                                  if currentlyParsing == "Records":
                                      # apply the parent hierarchical labels, just stored in simple globals
                                      # info of the
                                      chunkInfo['RecordName'] = currentRecordName
                                      chunkInfo['RecordLabel'] = currentRecordLabel
                                      chunkInfo['RecordTypeValue'] = currentRecordType.strip("'")
                                      chunkInfo['LevelName'] = currentLevelName
                                      chunkInfo['LevelLabel'] = currentLevelLabel
                                      chunkInfo['FileCode']=currentSurveyCode
                                      if not 'ZeroFill' in chunkInfo:
                                          chunkInfo['ZeroFill'] = currentSurveyZeroFill
                                      if not 'DecimalChar' in chunkInfo:
                                          chunkInfo['DecimalChar'] = currentSurveyDecChar

                                      # "save" the information to the output list
                                      myItems.append(chunkInfo)
                                  elif currentlyParsing == "IdItems":
                                      # this is a special case; it needs to be written out as an "item" for
                                      # each record. In the .dcf, IdItems comes after level info but before record
                                      # info. So save the info into dirty globals so that when we parse the record
                                      # info that follows we have access to it.
                                      currentIdName = chunkInfo['Name']
                                      currentIdLabel = chunkInfo['Label']
                                      currentIdStart = chunkInfo['Start']
                                      currentIdLength = chunkInfo['Len']
                      else:
                          # We are "within" a chunk of information
                          # add item key / value to the current chunk dictionary
                          # There are sometimes lines with more than one equals sign in (as it can appear in the
                          # description) so split at the FIRST = position only and clear up a bit (carriage return)
                          splitPos = line.find('=')
                          fieldName = line[0:splitPos].strip()
                          fieldVal = line[splitPos+1:].strip()
                          #fieldName,fieldVal = line.split('=')

                          if fieldName == 'Value':
                              # we don't explicitly check that we're in a valueset chunk, but we will be(?)

                              # match value ranges based on pattern "digits-colon-digits"
                              # Add these to a separate list of valueranges, because we will write them out differently
                              # depending on whether there is one or more than one range specified
                              if re.match('\d+:\d+', fieldVal):
                                  try:
                                      # again don't just split and unpack, in case there is a colon in the description too
                                      splitPos = fieldVal.find(':')
                                      vMin = fieldVal[0:splitPos].strip()
                                      vMax = fieldVal[splitPos+1:].strip()
                                      # the right hand side sometimes contains a description of the range values
                                      # after a semicolon
                                      if re.match('\d+;', vMax):
                                          splitPos = vMax.find(';')
                                          vMaxNew = vMax[0:splitPos]
                                          valDesc = vMax[splitPos+1:]
                                          vMax = vMaxNew
                                      # if it doesn't then use the valueset label instead
                                      else:
                                      #    valDesc = chunkInfo['Label']
                                          valDesc = ''
                                  except:
                                      print "uhoh!"
                                      print fieldVal
                                      print chunkInfo

                                      valRange, otherCrap = fieldVal.split(';')
                                      vMin,vMax = valRange.split(':')
                                  #colonPos = fieldVal.find(':')
                                  if not 'ValueRanges' in chunkInfo:
                                      chunkInfo['ValueRanges'] = []
                                  chunkInfo['ValueRanges'].append((vMin, vMax, valDesc.strip()))
                                  #chunkInfo['Range_Low_Value'] = vMin
                                  #chunkInfo['Range_High_Value'] = vMax
                                  #chunkInfo['Range_Desc'] = valDesc.strip()

                              # match "normal" value/description pairs based on digits-semicolon
                              elif re.match('\d+;', fieldVal):
                                  # split at pos of first semicolon
                                  scPos = fieldVal.find(';')
                                  val = fieldVal[0:scPos]
                                  valDesc = fieldVal[scPos+1:]
                                  # do not just split at semicolon because semicolon might also occur within the desc
                                  #val, valDesc = fieldVal.split(';')
                                  currentValues.append((val.strip(),valDesc.strip(), "ExplicitValue"))

                              # match horrible lines with VALUE given as string with quotes (see VCAL_VS1)
                              elif re.match('.+;', fieldVal):
                                  scPos = fieldVal.find(';')
                                  val = fieldVal[0:scPos]
                                  valDesc = fieldVal[scPos+1:]
                                  #val, valDesc = fieldVal.split(';')
                                  currentValues.append((val.strip("'").strip(),valDesc.strip("'").strip(), "ExplicitValue"))

                              # else save whatever we've got, presumably there is a value with no desc
                              else:
                                  currentValues.append((fieldVal,"", "ExplicitValue"))

                          elif not chunkInfo.has_key(fieldName):
                              # append the first occurrence of other labels. Subsequent ones will be silently discarded
                              chunkInfo[fieldName] = fieldVal
                  print "Parsed {0!s} lines into {1!s} items".format(parsedLines,len(myItems))
                  return myItems


          def input(self, feature):
              self.dcfFile = feature.getAttribute('dcfFN')
              parsedDCF = self.parseDCF(self.dcfFile)
              reqFieldNames = ['FileCode','RecordName','RecordTypeValue','RecordLabel','Name','Label','Start','Len','Occurrences',
                       'ZeroFill', 'DecimalChar', 'Decimal', 'FMETYPE']
              for item in parsedDCF:
                  if 'Values' in item and len(item['Values'])>0:
                      vals = item['Values']
                      for val in vals:
                          feature = fmeobjects.FMEFeature()
                          feature.setAttribute('FileCode',item['FileCode'])
                          feature.setAttribute('Name', item['Name'])
                          feature.setAttribute('Value', val[0])
                          feature.setAttribute('ValueDesc', val[1])
                          feature.setAttribute('ValueType', val[2])
                          self.pyoutput(feature)

          def __init__(self):
              pass
          def close(self):
              pass
    PYTHONSYMBOL = FeatureCreator
    NEW_ATTRIBUTES = FileCode Name Value ValueDesc ValueType

Bookmark: Unused - these tables will be populated one-off
Note: TODO - We can READ these tables and use featuremergers to check that referential integrity is maintained
