FME workspace import_dhs_survey_metadata_from_dcfs_old.fmw

Parameters:
- SourceDataset_CSV = C:\Users\zool1301\Documents\DHS\Phase5\SurveySpecs_Final\ALIR50.FlatRecordSpec.csv   # Source CSV (CommaSeparatedValue) File(s)
- SourceDataset_CSV_5 = C:\Users\zool1301\Documents\DHS\Phase5\SurveySpecs_Final\ALIR50.FlatValuesSpec.csv   # Source CSV (CommaSeparatedValue) File(s)
- SurveyIDMapFile = C:\Users\zool1301\Documents\DHS\DHS_Info\SurveyIdsByFile_P5.csv   # CSV file containing mapping between different survey ID systems
- DestDataset_POSTGRES = staging_rw@map.zoo.ox.ac.uk:5434/staging   # Output DB connection
- dcf_file = C:\Users\zool1301\Documents\DHS\Phase5\ExtractedSurveysAndShapes\BOIR51.DCF   # dcf filename
- SourceDataset_PATH = C:\Users\zool1301\Documents\DHS\Phase5\ExtractedSurveysAndShapes   # Source Folder and File Pathnames Folder
- SourceDataset_POSTGRES = staging_rw@map.zoo.ox.ac.uk:5434/staging   # Connection

Readers:
- CSV_1: CSV from $(SurveyIDMapFile)
- CSV_2: CSV from $(SourceDataset_CSV)
- CSV_3: CSV from $(SourceDataset_CSV_5)
- PATH_1: PATH from $(SourceDataset_PATH)
- POSTGRES_3: POSTGRES from $(SourceDataset_POSTGRES)

Writers:
- POSTGRES_1: POSTGRES to $(DestDataset_POSTGRES)
- POSTGRES_2: POSTGRES to $(DestDataset_POSTGRES)

Note: Survey id mapping
CSV (reader CSV_1)
    attributes: SurveyFilename char(7), Country char(22), Year char(8), Survey_ID_num number(4,0), SurveyAPI_ID char(10), Type char(4)
    -> FeatureMerger [input 2]
FeatureReader
    POSTGRES_NAMED_CONNECTION = staging_rw@map.zoo.ox.ac.uk:5434/staging
    DATASET = staging_rw@map.zoo.ox.ac.uk:5434/staging
    FEATURETYPES = dhs.dhs_surveys
    FORMAT = POSTGRES
    POSTGRES_QUERY_FEATURE_TYPES_FOR_MERGE_FILTERS = Yes
    ATTRIBUTES = dhs.dhs_surveys,"dhs_file_code,dhs_numeric_id,dhs_api_id,record_type_start,record_type_len,country_specific"
    ATTR_ACCUM_MODE = Only Use Result
    COMBINE_GEOM = Use Result
    POSTGRES_SCHEMALIST = dhs
    WHERE = dhs_file_code = '@Value(dhs_file_code)'
    OUTPUT_FEATURES_DISPLAY = Based on Connections
    FEATURETYPES_RADIO = FEATURETYPES
    dhs.dhs_surveys -> Terminator_5
Terminator_5
    MESSAGE = This survey is already in the database! Translation Terminated!
Note: Attach the information that relates the different DHS identifier systems
FeatureMerger
    SUPPLIERS_FIRST = No
    ATTR_CONFLICT_RES = Use Requestor
    PROCESS_DUPS = No
    ATTR_ACCUM_MODE = Merge Supplier
    MERGE_TYPE = Attributes Only
    JOIN_KEYS = @Value(dhs_file_code) @Value(SurveyFilename) AUTO
    IGNORE_NULLS = No
    MERGED -> AttributeRenamer_2
    NOT_MERGED -> Terminator_4
AttributeRenamer_2
    ATTR_LIST = start,record_type_start,,len,record_type_len,,SurveyAPI_ID,dhs_api_id,,Survey_ID_num,dhs_numeric_id,
    -> dhs.dhs_surveys (writer POSTGRES_1)
    -> AttributeKeeper
Note: This table stores information that is necessary to being parsing a data file, specifically where in the line to look for the record type
Note: dhs_file_code provides the top level common link / TODO / - could add phase number, survey type, etc to this table or just create a view, as they are encapsulated in the file name / - country_specific likewise
dhs.dhs_surveys (writer POSTGRES_1)
    attributes: dhs_numeric_id int4, dhs_api_id varchar(10), record_type_start int4, record_type_len int4, dhs_file_code varchar(8),PRIKEY, country_specific bool
AttributeKeeper
    KEEP_ATTRS = dhs_file_code
    -> FeatureMerger_2 [input 2]
Terminator_4
    MESSAGE = Translation Terminated! Survey ID info not found in file for @Value(dhs_file_code)
Note: Process survey definition
Note: Process record type definition
Note: The first feature in the spec file for each record type (the rows are ordered by record type) defines the unique identifier for that record type (table)
Sampler_2
    SAMPLE_TYPE_LONG = First N Features
    GROUP_BY = record_code dhs_file_code
    RATE = 1
    SAMPLED -> AttributeRenamer_3
    NOT_SAMPLED -> FeatureMerger_3 [input 1]
AttributeRenamer_3
    ATTR_LIST = Name,id_var_name,,start,id_var_start,,len,id_var_len,,RecordTypeValue,record_type_val,,RecordLabel,record_desc,
    -> FeatureMerger_2 [input 1]
Note: Check we will not violate integrity, i.e. that the survey information is present
FeatureMerger_2
    SUPPLIERS_FIRST = No
    ATTR_CONFLICT_RES = Use Requestor
    PROCESS_DUPS = No
    ATTR_ACCUM_MODE = Merge Supplier
    MERGE_TYPE = Attributes Only
    JOIN_KEYS = @Value(dhs_file_code) @Value(dhs_file_code) AUTO
    IGNORE_NULLS = No
    MERGED -> SQLExecutor_3
    NOT_MERGED -> Terminator
Note: Add record id - we have to get this from the DB sequence thus making a query to the DB for every record we will be writing! / (It may be better to use the natural key of survey file and record name)
SQLExecutor_3
    COMBINE_GEOM = Initiator Geometry Only
    SQL_STATEMENT = select nextval('dhs.dhs_gen_id_seq'::regclass) as id
    POSTGRES_QUERY_FEATURE_TYPES_FOR_MERGE_FILTERS = Yes
    DATASET = staging_rw@map.zoo.ox.ac.uk:5434/staging
    EXPOSED_ATTRIBUTE_LIST = id
    FORMAT = POSTGRES
    COMBINE_ATTRS = Keep Initiator Attributes if Conflict
    POSTGRES_NAMED_CONNECTION = staging_rw@map.zoo.ox.ac.uk:5434/staging
    RESULT -> dhs.dhs_records (writer POSTGRES_1)
    RESULT -> AttributeKeeper_2
Note: dhs_file_code has FK to dhs_surveys so surveys must be loaded first - the feature merger will delay the features such that this is true
dhs.dhs_records (writer POSTGRES_1)
    attributes: record_code varchar(10), record_desc varchar(120), dhs_file_code varchar(80), record_type_val varchar(4), id_var_name varchar(30), id_var_start int4, id_var_len int4, id int4,PRIKEY
AttributeKeeper_2
    KEEP_ATTRS = dhs_file_code,id,record_code
    -> AttributeRenamer_4
AttributeRenamer_4
    ATTR_LIST = id,record_id,
    -> FeatureMerger_3 [input 2]
Note: Process recode (item) definition
Note: Get the id of the record to which this recode (item) belongs.
FeatureMerger_3
    SUPPLIERS_FIRST = No
    ATTR_CONFLICT_RES = Use Requestor
    PROCESS_DUPS = No
    ATTR_ACCUM_MODE = Merge Supplier
    MERGE_TYPE = Attributes Only
    JOIN_KEYS = @Value(dhs_file_code) @Value(dhs_file_code) AUTO @Value(record_code) @Value(record_code) AUTO
    IGNORE_NULLS = No
    NOT_MERGED -> Terminator_2
    MERGED -> AttributeRenamer_7
AttributeRenamer_7
    ATTR_LIST = Name,recode,
    -> Tester
Note: TODO - restructure this to fit range values being in separate table / Is it a range-valued attribute?
Tester
    TEST_CLAUSE:
      TEST range_low_value NOT_ATTRIBUTE_VALUE_NULL ""
      TEST range_high_value NOT_ATTRIBUTE_VALUE_NULL ""
      TEST range_low_value NOT_ATTRIBUTE_IS_MISSING ""
      TEST range_high_value NOT_ATTRIBUTE_IS_MISSING ""
      TEST range_low_value NOT_ATTRIBUTE_IS_EMPTY ""
      TEST range_high_value NOT_ATTRIBUTE_IS_EMPTY ""
    TEST_DESCRIPTION = ""
    BOOL_OP = AND
    TEST_MODE = Automatic
    PASSED -> AttributeCreator
    FAILED -> FeatureMerger_5 [input 1]
Note: Yes, set flag R
AttributeCreator
    ATTR_LIST = recode_data_type,R
    -> SQLExecutor_2
Note: i'll be back
Terminator_2
    MESSAGE = Translation Terminated! No corresponding record info found for item @Value(Name) in file @Value(dhs_file_code)
Terminator
    MESSAGE = Translation Terminated! No corresponding survey info found for record @Value(record_code) in file @Value(dhs_file_code)
Note: We should only have one entry for each file/record/value combination and this is enforced in the DB. / But sometimes the data are a bit crap and so all we can do if we do find duplicates is discard the extras.
DuplicateRemover
    KEYATTR = FileCode Name Value
    DUPLICATE -> WARNING_Duplicate_Values_Discarded
    UNIQUE -> FeatureMerger_4 [input 1]
    UNIQUE -> StatisticsCalculator
StatisticsCalculator
    MAX_ATTR = _vals_max
    MIN_ATTR = _vals_min
    STATS_ATTRS = Value
    NUMERIC_ATTR = _vals_numeric_count
    GROUP_BY = FileCode Name
    PREPEND_ATTR_NAME_CHOICE = For multiple results only
    COUNT_ATTR = _vals_count
    COMPUTE_HISTOGRAM = NO
    SUMMARY -> Tester_2
Note: There are some values for almost everything, as even Free Text ones have value(s) for missing or N/A. / We determine whether the values found mean this variable has a value list or is just free text + missing by saying if there are fewr than three values and the lowest of them is greater than 7 then it's probablly just defining missing values on a free-text field
Tester_2
    TEST_CLAUSE:
      TEST @Value(_vals_count) < 3
      TEST @Value(_vals_min) > 7
    TEST_DESCRIPTION = ""
    BOOL_OP = AND
    TEST_MODE = Automatic
    PASSED -> FeatureMerger_5 [input 2]
Note: Is it free text valued attribute
FeatureMerger_5
    SUPPLIERS_FIRST = No
    ATTR_CONFLICT_RES = Use Requestor
    PROCESS_DUPS = No
    ATTR_ACCUM_MODE = Merge Supplier
    MERGE_TYPE = Attributes Only
    JOIN_KEYS = @Value(dhs_file_code) @Value(FileCode) AUTO @Value(recode) @Value(Name) AUTO
    IGNORE_NULLS = No
    MERGED -> AttributeCreator_2
    NOT_MERGED -> AttributeCreator_3
Note: Yes, set flag F
AttributeCreator_2
    ATTR_LIST = recode_data_type,F
    -> SQLExecutor_2
Note: No, set flag L
AttributeCreator_3
    ATTR_LIST = recode_data_type,L
    -> SQLExecutor_2
SQLExecutor_2
    COMBINE_GEOM = Initiator Geometry Only
    SQL_STATEMENT = select nextval('dhs.dhs_gen_id_seq'::regclass) as id
    POSTGRES_QUERY_FEATURE_TYPES_FOR_MERGE_FILTERS = Yes
    DATASET = staging_rw@map.zoo.ox.ac.uk:5434/staging
    EXPOSED_ATTRIBUTE_LIST = id
    FORMAT = POSTGRES
    COMBINE_ATTRS = Keep Initiator Attributes if Conflict
    POSTGRES_NAMED_CONNECTION = staging_rw@map.zoo.ox.ac.uk:5434/staging
    RESULT -> AttributeKeeper_3
    RESULT -> SubstringExtractor
SubstringExtractor
    END = 1
    SRC_STRING = @Value(dhs_file_code)
    RESULT_ATTR = country_code
    START = 0
    -> SubstringExtractor_2
SubstringExtractor_2
    END = 4
    SRC_STRING = @Value(dhs_file_code)
    RESULT_ATTR = phase_number
    START = 4
    -> SubstringExtractor_3
SubstringExtractor_3
    END = 99
    SRC_STRING = @Value(recode_description)
    RESULT_ATTR = recode_description
    START = 0
    -> dhs.dhs_recodes (writer POSTGRES_2)
Note: This is on the second writer (ordered in the navigator window). / This ensures it gets written after the tables referenced in its foreign key.
Note: Alternative to using multiple writers would be to disable the FK constraints when starting the workbench and renable at the end. / Use these SQL statements to create the scrtipts that should then be run at start and end to do this (taken from http://stackoverflow.com/questions/139884/how-do-i-disable-referential-integrity-in-postgres-8-2): / Start: / SELECT 'ALTER TABLE '||nspname||'.'||relname||' DROP CONSTRAINT '||conname||';' / FROM pg_constraint / INNER JOIN pg_class ON conrelid=pg_class.oid / INNER JOIN pg_namespace ON pg_namespace.oid=pg_class.relnamespace / ORDER BY CASE WHEN contype='f' THEN 0 ELSE 1 END,contype,nspname,relname,conname / End: / SELECT 'ALTER TABLE '||nspname||'.'||relname||' ADD CONSTRAINT '||conname||' '|| pg_get_constraintdef(pg_constraint.oid)||';' / FROM pg_constraint / INNER JOIN pg_class ON conrelid=pg_class.oid / INNER JOIN pg_namespace ON pg_namespace.oid=pg_class.relnamespace / ORDER BY CASE WHEN contype='f' THEN 0 ELSE 1 END DESC,contype DESC,nspname DESC,relname DESC,conname DESC;
Note: NOTE: / - country code, phase number and survey type code are all encapsulated in the filecode,which is stored at the top of the hierarchy in the survey table thanks to FK on record_id) / - currently not storing the dhs items data_type (dhs_data_type), item_type (is_sub_item) - these are set to dummy values / - i would prefer to use a term like "item", "dhs_item", "variable", or "dhs_variable" rather than "recode" throughout / - what about booleans?
dhs.dhs_recodes (writer POSTGRES_2)
    attributes: recode varchar(12),BTREE, recode_data_type varchar(2),BTREE, recode_description varchar(100), start int4, len int4, dhs_dec int4, zero_fill bool, id int4,PRIKEY, occurrences int4, is_sub_item bool, has_decimal_char bool, dhs_data_type char(2), record_id int4
AttributeKeeper_3
    KEEP_ATTRS = dhs_file_code,id,recode
    -> AttributeRenamer_5
AttributeRenamer_5
    ATTR_LIST = id,recode_id,
    -> FeatureMerger_4 [input 2]
Note: Get the id of the recode to which this value belongs
FeatureMerger_4
    SUPPLIERS_FIRST = No
    ATTR_CONFLICT_RES = Use Requestor
    PROCESS_DUPS = No
    ATTR_ACCUM_MODE = Merge Supplier
    MERGE_TYPE = Attributes Only
    JOIN_KEYS = @Value(FileCode) @Value(dhs_file_code) AUTO @Value(Name) @Value(recode) AUTO
    IGNORE_NULLS = No
    NOT_MERGED -> Terminator_3
    MERGED -> FeatureMerger_6 [input 1]
Note: I am unable to comply
Terminator_3
    MESSAGE = Translation Terminated! No corresponding recode info found for value @Value(Name) - @Value(Value) in file @Value(FileCode)
WARNING_Duplicate_Values_Discarded: Inspector
dhs.dhs_recode_value_types (reader POSTGRES_3)
    attributes: value_type int4,PRIKEY, value_type_desc varchar(50), value_type_short_desc varchar(15),PRIKEY
    -> FeatureMerger_6 [input 2]
FeatureMerger_6
    SUPPLIERS_FIRST = Yes
    ATTR_CONFLICT_RES = Use Requestor
    PROCESS_DUPS = No
    ATTR_ACCUM_MODE = Merge Supplier
    MERGE_TYPE = Attributes Only
    JOIN_KEYS = @Value(ValueType) @Value(value_type_short_desc) AUTO
    IGNORE_NULLS = No
    MERGED -> SQLExecutor
Note: Get an identifier from the database
SQLExecutor
    COMBINE_GEOM = Initiator Geometry Only
    SQL_STATEMENT = select nextval('dhs.dhs_gen_id_seq'::regclass) as id
    POSTGRES_QUERY_FEATURE_TYPES_FOR_MERGE_FILTERS = Yes
    DATASET = staging_rw@map.zoo.ox.ac.uk:5434/staging
    EXPOSED_ATTRIBUTE_LIST = id
    FORMAT = POSTGRES
    COMBINE_ATTRS = Keep Initiator Attributes if Conflict
    POSTGRES_NAMED_CONNECTION = staging_rw@map.zoo.ox.ac.uk:5434/staging
    RESULT -> AttributeRenamer_6
AttributeRenamer_6
    ATTR_LIST = Value,value_code,,ValueDesc,value_description,
    -> SubstringExtractor_4
SubstringExtractor_4
    END = 119
    SRC_STRING = @Value(value_description)
    RESULT_ATTR = value_description
    START = 0
    -> dhs.dhs_recode_values (writer POSTGRES_2)
Note: This is on the second writer (ordered in the navigator window). / This ensures it gets written after the tables referenced in its foreign key, / and the feature merger means it will end up going after the recodes
dhs.dhs_recode_values (writer POSTGRES_2)
    attributes: id int4,PRIKEY, recode_id int4,BTREE, value_code varchar(10), value_description varchar(120), value_type int4
Note: Note! Joiner might be more efficient here but it doesn't seem to work with named connections. It says there was no password supplied... Bug!
Joiner [off]
    CACHE_SIZE = 5000
    FORMAT = POSTGRES
    MATCH_RULE_DISPLAY = Must Match Exactly One (1:1)
    PREFETCH_EXHAUSTIVE = Yes
    POSTGRES_QUERY_FEATURE_TYPES_FOR_MERGE_FILTERS = Yes
    TABLE = dhs.dhs_recode_value_types
    ADDED_FIELDS = value_type
    JOIN_KEYS = ValueType value_type_short_desc
    POSTGRES_NAMED_CONNECTION = staging_rw@map.zoo.ox.ac.uk:5434/staging
    DATASET = staging_rw@map.zoo.ox.ac.uk:5434/staging

Bookmark: Data input method 1: From files
Note: Record / item information - generated by python script which parses .DCF specificztion file into a flat CSV
CSV (reader CSV_2)
    attributes: FileCode char(7), RecordName char(7), RecordTypeValue char(4), RecordLabel char(50), Name char(12), Label char(77), Start number(4,0), Len number(3,0), Occurrences number(3,0), FMETYPE char(13), ZeroFill char(4), DecimalChar char(3), Decimal char(1)
    -> AttributeRenamer
Note: Values information
CSV (reader CSV_3)
    attributes: FileCode char(7), Name char(10), Value number(7,0), ValueDesc char(53), ValueType char(14)
    -> DuplicateRemover

Bookmark: Data input method 2: Read directory of DCF files
Note: Use this approach to just run all DCFs in a directory.
PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> AttributeRenamer_8
AttributeRenamer_8
    ATTR_LIST = path_windows,dcfFN,
    -> AttributeKeeper_4

Bookmark: Data input method 3: Read DCF file from parameter
Note: Use this approach for best performance by running several copies of this WB at once from an external WB that has a path reader and runs several in parallel via WorkspaceRunner
Creator [off]
    NUM = 1
    GEOMTYPE = Geometry Object
    CREATED -> ParameterFetcher
ParameterFetcher
    ATTR_LIST = dcfFN {$(dcf_file)}
    -> AttributeKeeper_4

Bookmark: Data input - run python parser
AttributeKeeper_4
    KEEP_ATTRS = dcfFN
    -> PythonCaller
    -> PythonCaller_2
Note: Parse DCF for recodes
PythonCaller
    NEW_ATTRIBUTES = FileCode RecordName RecordTypeValue RecordLabel Name Label Start Len Occurrences ZeroFill DecimalChar Decimal FMETYPE
    PYTHONSOURCE:
      import fmeobjects
      from operator import itemgetter
      import re
      import os
      from difflib import SequenceMatcher as SM

      class FeatureCreator(object):
          # We simply read the .DCF format file in line order, imputing the hierarchical structure from the order
      # of things, i.e. the level and record of an item is the previous found level or record
      # We also take advantage of the blank line between chunks as a line delimiter.

          def parseDCF(self, dcfFile):
              global parsedLines
              parsedLines = 0

              currentRecordName = 'N/A'
              currentRecordLabel = 'N/A'
              currentRecordType = 'N/A'
              currentLevelName = ''
              currentLevelLabel = ''

              currentValues = []
              skippingChunk = False

              currentlyParsing = "None"
              currentIdName = "None"
              currentIdLabel = "None"
              currentIdStart = 0
              currentIdLength = 0

              myRecords = {}
              myLevels = {}
              myItems = []
              myCountries = {}
              mySkippedChunks = []
              currentSurveyCode = os.path.basename(dcfFile).split(os.extsep)[0]
              chunkInfo = {
                  'FileCode':currentSurveyCode
              }

              #with open(r'C:\Users\zool1301\Documents\DHS\Namibia_Test\Hierarchical Format\NMIR60.DCF') as fileIn:
              with open(dcfFile) as fileIn:
              #with open(r'C:\Users\zool1301\Documents\DHS\RecodeManuals\MRecode6.dcf') as fileIn:

                  for line in fileIn:
                      parsedLines +=1
                      # Are we on a chunk start (a line with something in [Brackets])?
                      if line.find('[Level]') != -1:
                          currentChunkType = "Level"
                          skippingChunk = False
                          chunkInfo = {}
                      elif line.find('[Record]') != -1:
                          currentChunkType = "Record"
                          currentlyParsing = "Records"
                          skippingChunk = False
                          chunkInfo = {}
                      elif line.find('[Item]') != -1:
                          currentChunkType = "Item"
                          skippingChunk = False
                          chunkInfo = {}
                      elif line.find('[ValueSet]') != -1:
                          currentChunkType = "ValueSet"
                          skippingChunk = False
                          chunkInfo = {}
                      elif line.find('[IdItems]') != -1:
                          currentChunkType = "IdItems"
                          skippingChunk = False
                          currentlyParsing = "IdItems"
                          currentIdStart = 0
                          currentIdLength = 0
                          currentIdName = "None"
                          chunkInfo = {}
                      elif line.find('[Dictionary]') != -1:
                          currentChunkType = "Dictionary"
                          currentlyParsing = "Dictionary"
                          skippingChunk = False
                          recordTypeStart = 0
                          recordTypeLen = 0

                      elif line.find('[') != -1 and line.find(']') != -1:
                          # This is some chunk we don't know and/or care about.
                          skippingChunk = True
                          mySkippedChunks.append(line)

                      # Or are we on the end of a chunk, marked by a blank line?
                      elif line == '\n':
                          if skippingChunk:
                              # this was a bunch of lines we skip (e.g. those following '[Dictionary]')
                              skippingChunk = False
                          else:
                              # If we're at the end of a chunk defining a level or record then place the
                              # info into the globals so that the item parser will read them for items
                              # that FOLLOW afterward
                              if currentChunkType == 'Level':
                                  currentLevelName = chunkInfo['Name']
                                  currentLevelLabel = chunkInfo['Label']
                                  if myLevels.has_key(currentLevelName):
                                      if myLevels[currentLevelName] == currentLevelLabel:
                                          print "Warning, duplicate level name/label encountered at line "+str(parsedLines)
                                      else:
                                          raise ValueError("Duplicate level name encountered at line {0!s} with non-matched label".
                                                           format(parsedLines))
                                  myLevels[currentLevelName] = currentLevelLabel

                              elif currentChunkType == 'Record':
                                  # save into dirty globals so the subsequent items know what record they belong to
                                  currentRecordName = chunkInfo['Name']
                                  currentRecordLabel = chunkInfo['Label']
                                  currentRecordType = chunkInfo['RecordTypeValue']

                                  # save an "item" with the new record name/type/label reflecting the
                                  # id item for this record. In other words the first output row of each record
                                  # will describe the record itself and in particular the start/len of the id item
                                  chunkInfo['FileCode']=currentSurveyCode
                                  chunkInfo['Name'] = currentIdName
                                  chunkInfo['Label'] = currentIdLabel
                                  chunkInfo['Start'] = currentIdStart
                                  chunkInfo['Len'] = currentIdLength
                                  # apply the parent hierarchical labels, just stored in simple globals
                                  chunkInfo['RecordName'] = currentRecordName
                                  chunkInfo['RecordLabel'] = currentRecordLabel
                                  chunkInfo['RecordTypeValue'] = currentRecordType.strip("'")
                                  chunkInfo['LevelName'] = currentLevelName
                                  chunkInfo['LevelLabel'] = currentLevelLabel
                                  myItems.append(chunkInfo)

                                  if myRecords.has_key(currentRecordName):
                                      if myRecords[currentRecordName] == currentRecordLabel:
                                          print "Warning, duplicate record name/label encountered at line "+str(parsedLines)
                                      else:
                                          raise ValueError("Duplicate record name encountered at line {0!s} with non-matched label".
                                                           format(parsedLines))
                                  myRecords[currentRecordName] = currentRecordLabel

                              #elif currentChunkType == 'Dictionary'

                              # If we're at the end of a chunk defining a valueset then place the info
                              # into the last-processed item - valueset comes AFTER the item and a blank line,
                              # so the item will have already been added to the output list myItems
                              elif currentChunkType == 'ValueSet':
                                  # check it matches-ish. Either starts the same or text similarity is high
                                  # - sometimes they abbreviate the valueset but not the previous label
                                  s1 = chunkInfo['Label']
                                  s2 = myItems[-1]['Label']
                                  simRatio = SM(None,s1,s2).ratio()
                                  if not (simRatio > 0.7 or chunkInfo['Label'].find(myItems[-1]['Label']) == 0):
                                      print ("Warning, valueset did not seem to match item at line {0!s} of file {1!s} - please check!".
                                             format(parsedLines,dcfFile))
                                  if myItems[-1].has_key('Values'):
                                          # one item in the file (potentially more in others?) has two valueset chunks!
                                      myItems[-1]['Values'].extend(currentValues)
                                  else:
                                      myItems[-1]['Values'] = currentValues
                                  if chunkInfo.has_key('Range_Low_Value'):
                                      myItems[-1]['Range_Low_Value'] = chunkInfo['Range_Low_Value']
                                  if chunkInfo.has_key('Range_High_Value'):
                                      myItems[-1]['Range_High_Value'] = chunkInfo['Range_High_Value']
                                  if chunkInfo.has_key('Range_Desc'):
                                      myItems[-1]['Range_Desc'] = chunkInfo['Range_Desc']
                                  currentValues = []
                                  #else:
                                  #    raise ValueError("Error parsing valueset at line "+str(parsedLines))

                              elif currentChunkType == 'Dictionary':
                                  # This will be the first item in the file and will be written to the first
                                  # row of the output. It's an item that describes for all lines of the data file
                                  # where the record type can be found (start/len)
                                  chunkInfo['RecordName'] = '*'
                                  chunkInfo['RecordLabel'] = '*'
                                  chunkInfo['RecordTypeValue'] = '*'
                                  chunkInfo['Start'] = chunkInfo['RecordTypeStart']
                                  chunkInfo['Len'] = chunkInfo['RecordTypeLen']
                                  myItems.append(chunkInfo)

                              # Otherwise we are at the end of a chunk defining an actual item (recode)
                              elif currentChunkType == 'Item':
                                  if currentlyParsing == "Records":
                                      # apply the parent hierarchical labels, just stored in simple globals
                                      chunkInfo['RecordName'] = currentRecordName
                                      chunkInfo['RecordLabel'] = currentRecordLabel
                                      chunkInfo['RecordTypeValue'] = currentRecordType.strip("'")
                                      chunkInfo['LevelName'] = currentLevelName
                                      chunkInfo['LevelLabel'] = currentLevelLabel
                                      # "save" the information to the output list
                                      chunkInfo['FileCode']=currentSurveyCode
                                      myItems.append(chunkInfo)
                                  elif currentlyParsing == "IdItems":
                                      # this is a special case; it needs to be written out as an "item" for
                                      # each record. In the .dcf, IdItems comes after level info but before record
                                      # info. So save the info into dirty globals so that when we parse the record
                                      # info that follows we have access to it.
                                      currentIdName = chunkInfo['Name']
                                      currentIdLabel = chunkInfo['Label']
                                      currentIdStart = chunkInfo['Start']
                                      currentIdLength = chunkInfo['Len']
                      else:
                          # We are "within" a chunk of information
                          # add item key / value to the current chunk dictionary
                          # There are sometimes lines with more than one equals sign in (as it can appear in the
                          # description) so split at the FIRST = position only and clear up a bit (carriage return)
                          splitPos = line.find('=')
                          fieldName = line[0:splitPos].strip()
                          fieldVal = line[splitPos+1:].strip()
                          #fieldName,fieldVal = line.split('=')
                          if fieldName == 'Value':
                              # match value ranges based on pattern digits-colon-digits
                              if re.match('\d+:\d+', fieldVal):
                                  # use tuple unpacking to ensure that if we hit multiple : we will fail cleanly
                                  try:
                                      vMin, vMax = fieldVal.split(':')
                                      # the right hand side sometimes contains a description of the range values
                                      # after a semicolon
                                      if re.match('\d+;', vMax):
                                          vMax, valDesc = vMax.split(';')
                                      else:
                                          valDesc = ''
                                  except:
                                      valRange, otherCrap = fieldVal.split(';')
                                      vMin,vMax = valRange.split(':')
                                  #colonPos = fieldVal.find(':')

                                  chunkInfo['Range_Low_Value'] = vMin
                                  chunkInfo['Range_High_Value'] = vMax
                                  chunkInfo['Range_Desc'] = valDesc.strip()
                              # match "normal" value/description pairs based on digits-semicolon
                              elif re.match('\d+;', fieldVal):
                                  scPos = fieldVal.find(';')
                                  val = fieldVal[0:scPos]
                                  valDesc = fieldVal[scPos+1:]
                                  #val, valDesc = fieldVal.split(';')
                                  currentValues.append((val.strip(),valDesc.strip()))
                              # match horrible lines with VALUE given as string with quotes (see VCAL_VS1)
                              elif re.match('.+;', fieldVal):
                                  scPos = fieldVal.find(';')
                                  val = fieldVal[0:scPos]
                                  valDesc = fieldVal[scPos+1:]
                                  #val, valDesc = fieldVal.split(';')
                                  currentValues.append((val.strip("'").strip(),valDesc.strip("'").strip()))
                              # else save whatever we've got, presumably there is a value with no desc
                              else:
                                  currentValues.append((fieldVal,""))

                          elif not chunkInfo.has_key(fieldName):
                              # append the first occurrence of other labels. Subsequent ones will be silently discarded
                              chunkInfo[fieldName] = fieldVal
                  print "Parsed {0!s} lines into {1!s} items".format(parsedLines,len(myItems))
                  return myItems

          def input(self, feature):
              self.dcfFile = feature.getAttribute('dcfFN')
              parsedDCF = self.parseDCF(self.dcfFile)
              reqFieldNames = ['FileCode','RecordName','RecordTypeValue','RecordLabel','Name','Label','Start','Len','Occurrences',
                       'Range_Low_Value', 'Range_High_Value', 'Range_Desc', 'FMETYPE']
              for item in parsedDCF:
                  feature = fmeobjects.FMEFeature()
                  for f in reqFieldNames:
                      if f in item:
                          feature.setAttribute(f,item[f])
                  feature.setAttribute("FMETYPE", "fme_char({0!s})".format(item['Len']))
                  self.pyoutput(feature)

          def __init__(self):
              pass
          def close(self):
              pass
    PYTHONSYMBOL = FeatureCreator
    -> AttributeRenamer
Note: Parse DCF for values
PythonCaller_2
    NEW_ATTRIBUTES = FileCode Name Value ValueDesc ValueType
    PYTHONSOURCE:
      import fmeobjects
      from operator import itemgetter
      import re
      import os
      from difflib import SequenceMatcher as SM

      class FeatureCreator(object):
          # We simply read the .DCF format file in line order, imputing the hierarchical structure from the order
      # of things, i.e. the level and record of an item is the previous found level or record
      # We also take advantage of the blank line between chunks as a line delimiter.

          def parseDCF(self, dcfFile):
              global parsedLines
              parsedLines = 0

              currentRecordName = 'N/A'
              currentRecordLabel = 'N/A'
              currentRecordType = 'N/A'
              currentLevelName = ''
              currentLevelLabel = ''

              currentValues = []
              skippingChunk = False

              currentlyParsing = "None"
              currentIdName = "None"
              currentIdLabel = "None"
              currentIdStart = 0
              currentIdLength = 0

              myRecords = {}
              myLevels = {}
              myItems = []
              myCountries = {}
              mySkippedChunks = []
              currentSurveyCode = os.path.basename(dcfFile).split(os.extsep)[0]
              chunkInfo = {
                  'FileCode':currentSurveyCode
              }

              #with open(r'C:\Users\zool1301\Documents\DHS\Namibia_Test\Hierarchical Format\NMIR60.DCF') as fileIn:
              with open(dcfFile) as fileIn:
              #with open(r'C:\Users\zool1301\Documents\DHS\RecodeManuals\MRecode6.dcf') as fileIn:

                  for line in fileIn:
                      parsedLines +=1
                      # Are we on a chunk start (a line with something in [Brackets])?
                      if line.find('[Level]') != -1:
                          currentChunkType = "Level"
                          skippingChunk = False
                          chunkInfo = {}
                      elif line.find('[Record]') != -1:
                          currentChunkType = "Record"
                          currentlyParsing = "Records"
                          skippingChunk = False
                          chunkInfo = {}
                      elif line.find('[Item]') != -1:
                          currentChunkType = "Item"
                          skippingChunk = False
                          chunkInfo = {}
                      elif line.find('[ValueSet]') != -1:
                          currentChunkType = "ValueSet"
                          skippingChunk = False
                          chunkInfo = {}
                      elif line.find('[IdItems]') != -1:
                          currentChunkType = "IdItems"
                          skippingChunk = False
                          currentlyParsing = "IdItems"
                          currentIdStart = 0
                          currentIdLength = 0
                          currentIdName = "None"
                          chunkInfo = {}
                      elif line.find('[Dictionary]') != -1:
                          currentChunkType = "Dictionary"
                          currentlyParsing = "Dictionary"
                          skippingChunk = False
                          recordTypeStart = 0
                          recordTypeLen = 0

                      elif line.find('[') != -1 and line.find(']') != -1:
                          # This is some chunk we don't know and/or care about.
                          skippingChunk = True
                          mySkippedChunks.append(line)

                      # Or are we on the end of a chunk, marked by a blank line?
                      elif line == '\n':
                          if skippingChunk:
                              # this was a bunch of lines we skip (e.g. those following '[Dictionary]')
                              skippingChunk = False
                          else:
                              # If we're at the end of a chunk defining a level or record then place the
                              # info into the globals so that the item parser will read them for items
                              # that FOLLOW afterward
                              if currentChunkType == 'Level':
                                  currentLevelName = chunkInfo['Name']
                                  currentLevelLabel = chunkInfo['Label']
                                  if myLevels.has_key(currentLevelName):
                                      if myLevels[currentLevelName] == currentLevelLabel:
                                          print "Warning, duplicate level name/label encountered at line "+str(parsedLines)
                                      else:
                                          raise ValueError("Duplicate level name encountered at line {0!s} with non-matched label".
                                                           format(parsedLines))
                                  myLevels[currentLevelName] = currentLevelLabel

                              elif currentChunkType == 'Record':
                                  # save into dirty globals so the subsequent items know what record they belong to
                                  currentRecordName = chunkInfo['Name']
                                  currentRecordLabel = chunkInfo['Label']
                                  currentRecordType = chunkInfo['RecordTypeValue']

                                  # save an "item" with the new record name/type/label reflecting the
                                  # id item for this record. In other words the first output row of each record
                                  # will describe the record itself and in particular the start/len of the id item
                                  chunkInfo['FileCode']=currentSurveyCode
                                  chunkInfo['Name'] = currentIdName
                                  chunkInfo['Label'] = currentIdLabel
                                  chunkInfo['Start'] = currentIdStart
                                  chunkInfo['Len'] = currentIdLength
                                  # apply the parent hierarchical labels, just stored in simple globals
                                  chunkInfo['RecordName'] = currentRecordName
                                  chunkInfo['RecordLabel'] = currentRecordLabel
                                  chunkInfo['RecordTypeValue'] = currentRecordType.strip("'")
                                  chunkInfo['LevelName'] = currentLevelName
                                  chunkInfo['LevelLabel'] = currentLevelLabel
                                  myItems.append(chunkInfo)

                                  if myRecords.has_key(currentRecordName):
                                      if myRecords[currentRecordName] == currentRecordLabel:
                                          print "Warning, duplicate record name/label encountered at line "+str(parsedLines)
                                      else:
                                          raise ValueError("Duplicate record name encountered at line {0!s} with non-matched label".
                                                           format(parsedLines))
                                  myRecords[currentRecordName] = currentRecordLabel

                              #elif currentChunkType == 'Dictionary'

                              # If we're at the end of a chunk defining a valueset then place the info
                              # into the last-processed item - valueset comes AFTER the item and a blank line,
                              # so the item will have already been added to the output list myItems
                              elif currentChunkType == 'ValueSet':
                                  # check it matches-ish. Either starts the same or text similarity is high
                                  # - sometimes they abbreviate the valueset but not the previous label
                                  s1 = chunkInfo['Label']
                                  s2 = myItems[-1]['Label']
                                  simRatio = SM(None,s1,s2).ratio()
                                  if not (simRatio > 0.7 or chunkInfo['Label'].find(myItems[-1]['Label']) == 0):
                                      print ("Warning, valueset did not seem to match item at line {0!s} of file {1!s} - please check!".
                                             format(parsedLines,dcfFile))
                                  if myItems[-1].has_key('Values'):
                                          # one item in the file (potentially more in others?) has two valueset chunks!
                                      myItems[-1]['Values'].extend(currentValues)
                                  else:
                                      myItems[-1]['Values'] = currentValues
                                  if chunkInfo.has_key('Range_Low_Value'):
                                      myItems[-1]['Range_Low_Value'] = chunkInfo['Range_Low_Value']
                                  if chunkInfo.has_key('Range_High_Value'):
                                      myItems[-1]['Range_High_Value'] = chunkInfo['Range_High_Value']
                                  if chunkInfo.has_key('Range_Desc'):
                                      myItems[-1]['Range_Desc'] = chunkInfo['Range_Desc']
                                  currentValues = []
                                  #else:
                                  #    raise ValueError("Error parsing valueset at line "+str(parsedLines))

                              elif currentChunkType == 'Dictionary':
                                  # This will be the first item in the file and will be written to the first
                                  # row of the output. It's an item that describes for all lines of the data file
                                  # where the record type can be found (start/len)
                                  chunkInfo['RecordName'] = '*'
                                  chunkInfo['RecordLabel'] = '*'
                                  chunkInfo['RecordTypeValue'] = '*'
                                  chunkInfo['Start'] = chunkInfo['RecordTypeStart']
                                  chunkInfo['Len'] = chunkInfo['RecordTypeLen']
                                  myItems.append(chunkInfo)

                              # Otherwise we are at the end of a chunk defining an actual item (recode)
                              elif currentChunkType == 'Item':
                                  if currentlyParsing == "Records":
                                      # apply the parent hierarchical labels, just stored in simple globals
                                      chunkInfo['RecordName'] = currentRecordName
                                      chunkInfo['RecordLabel'] = currentRecordLabel
                                      chunkInfo['RecordTypeValue'] = currentRecordType.strip("'")
                                      chunkInfo['LevelName'] = currentLevelName
                                      chunkInfo['LevelLabel'] = currentLevelLabel
                                      # "save" the information to the output list
                                      chunkInfo['FileCode']=currentSurveyCode
                                      myItems.append(chunkInfo)
                                  elif currentlyParsing == "IdItems":
                                      # this is a special case; it needs to be written out as an "item" for
                                      # each record. In the .dcf, IdItems comes after level info but before record
                                      # info. So save the info into dirty globals so that when we parse the record
                                      # info that follows we have access to it.
                                      currentIdName = chunkInfo['Name']
                                      currentIdLabel = chunkInfo['Label']
                                      currentIdStart = chunkInfo['Start']
                                      currentIdLength = chunkInfo['Len']
                      else:
                          # We are "within" a chunk of information
                          # add item key / value to the current chunk dictionary
                          # There are sometimes lines with more than one equals sign in (as it can appear in the
                          # description) so split at the FIRST = position only and clear up a bit (carriage return)
                          splitPos = line.find('=')
                          fieldName = line[0:splitPos].strip()
                          fieldVal = line[splitPos+1:].strip()
                          #fieldName,fieldVal = line.split('=')
                          if fieldName == 'Value':
                              # match value ranges based on pattern digits-colon-digits
                              if re.match('\d+:\d+', fieldVal):
                                  # use tuple unpacking to ensure that if we hit multiple : we will fail cleanly
                                  try:
                                      vMin, vMax = fieldVal.split(':')
                                      # the right hand side sometimes contains a description of the range values
                                      # after a semicolon
                                      if re.match('\d+;', vMax):
                                          vMax, valDesc = vMax.split(';')
                                      else:
                                          valDesc = ''
                                  except:
                                      valRange, otherCrap = fieldVal.split(';')
                                      vMin,vMax = valRange.split(':')
                                  #colonPos = fieldVal.find(':')

                                  chunkInfo['Range_Low_Value'] = vMin
                                  chunkInfo['Range_High_Value'] = vMax
                                  chunkInfo['Range_Desc'] = valDesc.strip()
                              # match "normal" value/description pairs based on digits-semicolon
                              elif re.match('\d+;', fieldVal):
                                  scPos = fieldVal.find(';')
                                  val = fieldVal[0:scPos]
                                  valDesc = fieldVal[scPos+1:]
                                  #val, valDesc = fieldVal.split(';')
                                  currentValues.append((val.strip(),valDesc.strip()))
                              # match horrible lines with VALUE given as string with quotes (see VCAL_VS1)
                              elif re.match('.+;', fieldVal):
                                  scPos = fieldVal.find(';')
                                  val = fieldVal[0:scPos]
                                  valDesc = fieldVal[scPos+1:]
                                  #val, valDesc = fieldVal.split(';')
                                  currentValues.append((val.strip("'").strip(),valDesc.strip("'").strip()))
                              # else save whatever we've got, presumably there is a value with no desc
                              else:
                                  currentValues.append((fieldVal,""))

                          elif not chunkInfo.has_key(fieldName):
                              # append the first occurrence of other labels. Subsequent ones will be silently discarded
                              chunkInfo[fieldName] = fieldVal
                  print "Parsed {0!s} lines into {1!s} items".format(parsedLines,len(myItems))
                  return myItems

          def input(self, feature):
              self.dcfFile = feature.getAttribute('dcfFN')
              parsedDCF = self.parseDCF(self.dcfFile)
              reqFieldNames = ['FileCode','RecordName','RecordTypeValue','RecordLabel','Name','Label','Start','Len','Occurrences',
                       'Range_Low_Value', 'Range_High_Value', 'Range_Desc', 'FMETYPE']
              for item in parsedDCF:
                  if 'Values' in item and len(item['Values'])>0:
                      vals = item['Values']
                      for val in vals:
                          feature = fmeobjects.FMEFeature()
                          feature.setAttribute('FileCode',item['FileCode'])
                          feature.setAttribute('Name', item['Name'])
                          feature.setAttribute('Value', val[0])
                          feature.setAttribute('ValueDesc', val[1])
                          self.pyoutput(feature)

          def __init__(self):
              pass
          def close(self):
              pass
    PYTHONSYMBOL = FeatureCreator
    -> DuplicateRemover

Bookmark: Data input
Note: TODO - transfer new python code to here
Note: Initial rename of attributes with common names in db
AttributeRenamer
    ATTR_LIST = FileCode,dhs_file_code,,Label,recode_description,,Len,len,,Start,start,,Occurrences,occurrences,,RecordName,record_code,,DecimalChar,has_decimal_char,,Decimal,dhs_dec,,ZeroFill,zero_fill,
    -> Sampler
Note: The first feature in the spec file defines how the record type can be read from all lines in the survey's data file
Sampler
    SAMPLE_TYPE_LONG = First N Features
    GROUP_BY = dhs_file_code
    RATE = 1
    SAMPLED -> FeatureMerger [input 1]
    NOT_SAMPLED -> Sampler_2
    SAMPLED -> FeatureReader

Bookmark: Unused - these tables will be populated one-off
Note: TODO - We can READ these tables and use featuremergers to check that referential integrity is maintained
