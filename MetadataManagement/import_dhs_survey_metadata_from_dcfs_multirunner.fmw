FME workspace import_dhs_survey_metadata_from_dcfs_multirunner.fmw

Parameters:
- SourceDataset_PATH = C:\Users\zool1301\Documents\DHS\Phase6_2\ExtractedSurveysAndShapes   # Source Folder and File Pathnames Folder

Readers:
- PATH_1: PATH from $(SourceDataset_PATH)

PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> WorkspaceRunner
Note: For now you need to point this to the survey ID mapping file manually...
Note: Runs 3 at once. Any more seemed to cause database issues.
WorkspaceRunner
    WORKSPACE_FILE = $(FME_MF_DIR)import_dhs_survey_metadata_from_dcfs.fmw
    BLOCKING = No
    WORKSPACE_PARAMETERS = CSV_RecordSpec,na,CSV_ValueSpec,na,SurveyIDMapFile,C:\Users\zool1301\Documents\DHS\DHS_Info\SurveyIdsByFile_P6_2.csv,DestDataset_POSTGRES,staging_rw@map.zoo.ox.ac.uk:5434/staging,dcf_file,@Value(path_windows),SourceDataset_PATH,na,SourceDataset_POSTGRES,staging_rw@map.zoo.ox.ac.uk:5434/staging,CountrySpecific,True
    MAX_PROC = 3
    SUCCEEDED -> WorkspaceRunner_Succeeded
    SUMMARY -> WorkspaceRunner_Summary
    FAILED -> WorkspaceRunner_Failed
WorkspaceRunner_Succeeded: Inspector
WorkspaceRunner_Failed: Inspector
WorkspaceRunner_Summary: Inspector
